FME workspace Dublin Fabrication Data Manager.fmw
Title: OSiDataTo3D

Parameters:
- DestDataset_STL_3 = /Users/mlinnane/repos/BCD-Interactive-City-Scale-Models/WIP/batch output tests   # Destination STL Folder
- ELEVATION = -8   # Planar Surface Elevation
- SourceDataset_LAS_5 = ""$(FME_MF_DIR)LiDAR_Footprints/Dublin_Clipped_PointCloud/a_FCIR_20170408_110916.las" "$(FME_MF_DIR)LiDAR_Footprints/Dublin_Clipped_PointCloud/a_FCIR_20170408_112657.las" "$(FME_MF_DIR)LiDAR_Footprints/Dublin_Clipped_PointCloud/a_FCIR_20170408_141111.las" "$(FME_MF_DIR)LiDAR_Footprints/Dublin_Clipped_PointCloud/a_FCIR_20170408_142635.las" "$(FME_MF_DIR)LiDAR_Footprints/Dublin_Clipped_PointCloud/a_FCIR_20170408_144524.las" "$(FME_MF_DIR)LiDAR_Footprints/Dublin_Clipped_PointCloud/b_FCIR_20170408_110916.las" "$(FME_MF_DIR)LiDAR_Footprints/Dublin_Clipped_PointCloud/b_FCIR_20170408_112657.las" "$(FME_MF_DIR)LiDAR_Footprints/Dublin_Clipped_PointCloud/b_FCIR_20170408_141111.las" "$(FME_MF_DIR)LiDAR_Footprints/Dublin_Clipped_PointCloud/b_FCIR_20170408_142635.las" "$(FME_MF_DIR)LiDAR_Footprints/Dublin_Clipped_PointCloud/b_FCIR_20170408_144524.las" "$(FME_MF_DIR)LiDAR_Footprints/Dublin_Clipped_PointCloud/c_FCIR_20170408_110916.las" "$(FME_MF_DIR)LiDAR_Footprints/Dublin_Clipped_PointCloud/c_FCIR_20170408_112657.las" "$(FME_MF_DIR)LiDAR_Footprints/Dublin_Clipped_PointCloud/c_FCIR_20170408_141111.las" "$(FME_MF_DIR)LiDAR_Footprints/Dublin_Clipped_PointCloud/c_FCIR_20170408_142635.las" "$(FME_MF_DIR)LiDAR_Footprints/Dublin_Clipped_PointCloud/c_FCIR_20170408_144524.las""   # Source ASPRS LAS File(s)
- SourceDataset_FILEGDB = $(FME_MF_DIR)LiDAR_Footprints/Dublin_City.gdb.zip   # File Geodatabase
- SourceDataset_ESRISHAPE_29 = $(FME_MF_DIR)Grids_Extents/Print Tiles Dublin Boundary 7x4km 1-2000 1km Tile/Print Tiles Dublin Boundary 7x4km 1-2000 1km Tile.shp   # Source Esri Shapefile(s)
- SourceDataset_ESRISHAPE_21 = /Users/mlinnane/Documents/github/BCD-Interactive-Architectural-City-Models/Grids/Non-national grid/120m2/Tiles 120m2.shp   # Source Esri Shapefile(s)
- SourceDataset_LAS = $(FME_MF_DIR)LiDAR_Footprints/Dublin_DTM/LiDAR_2009_Hackathon_Dublin_2m_DTM.xyz.las   # Source ASPRS LAS File(s)
- DestDataset_ESRISHAPE = /Users/mlinnane/repos/BCD-Interactive-City-Scale-Models/WIP   # Destination Esri Shapefile Folder
- DestDataset_OGCKML_5 = /Users/mlinnane/repos/BCD-Interactive-City-Scale-Models/WIP/Validation Tiles   # Destination Google KML File
- SourceDataset_ESRISHAPE_20 = $(FME_MF_DIR)Grids_Extents/Boundary Dublin 7x4km 1-2000   # Source Esri Shapefile(s)
- DestDataset_OBJ = /Users/mlinnane/repos/BCD-Interactive-City-Scale-Models/WIP/OBJ   # Destination OBJ Folder
- SourceDataset_ESRISHAPE_34 = $(FME_MF_DIR)Validation/Repaired Bridges/Repaired Bridges.shp   # Source Esri Shapefile(s)
- SourceDataset_CSV2 = $(FME_MF_DIR)Validation/Building Poly Repair List.csv   # Source CSV (Comma Separated Value) File(s)
- SourceDataset_CSV2_5 = $(FME_MF_DIR)Validation/Water Exceptions List.csv   # Source CSV (Comma Separated Value) File(s)
- SourceDataset_ESRISHAPE_28 = $(FME_MF_DIR)Grids_Extents/Sea/Sea.shp   # Source Esri Shapefile(s)
- SourceDataset_CSV2_4 = $(FME_MF_DIR)Validation/Core Artificial Poly Attribute Filter.csv   # Source CSV (Comma Separated Value) File(s)
- SourceDataset_ESRISHAPE_30 = $(FME_MF_DIR)Grids_Extents/Print Tiles Dublin Boundary 7x4km 1-2000 1km Tile/Print Tiles Dublin Boundary 7x4km 1-2000 1km Tile.shp   # Source Esri Shapefile(s)
- SourceDataset_ESRISHAPE_31 = $(FME_MF_DIR)Grids_Extents/Review Tiles Dublin Boundary 7x4km 1-2000 500m Tile   # Source Esri Shapefile(s)
- SourceDataset_ESRISHAPE_32 = $(FME_MF_DIR)Grids_Extents/Circle/Circle.shp   # Source Esri Shapefile(s)
- SourceDataset_ESRISHAPE_19 = $(FME_MF_DIR)Validation/Repaired Features/Repaired Features.shp   # Source Esri Shapefile(s)
- DestDataset_IEPS = /Users/mlinnane/repos/BCD-3D-Print-Master-Files/Dublin/Dublin Model Circles.eps   # Destination Adobe Illustrator EPS File
- DestDataset_IEPS_3 = /Users/mlinnane/Desktop/test.eps   # Destination Adobe Illustrator EPS File
- DestDataset_FBX = /Users/mlinnane/repos/BCD-Interactive-City-Scale-Models/WIP/FBX   # Destination FBX Folder
- DestDataset_GEOJSON = /Users/mlinnane/repos/BCD-Interactive-City-Scale-Models/WIP/FBX/tile19test.json   # Destination GeoJSON File

Readers:
- LAS_1: LAS from $(SourceDataset_LAS_5)
- FILEGDB_1: FILEGDB from $(SourceDataset_FILEGDB)
- ESRISHAPE_1: ESRISHAPE from $(SourceDataset_ESRISHAPE_29)
- ESRISHAPE_2: ESRISHAPE from $(SourceDataset_ESRISHAPE_21)
- LAS_2: LAS from $(SourceDataset_LAS)
- ESRISHAPE_3: ESRISHAPE from $(SourceDataset_ESRISHAPE_20)
- ESRISHAPE_4: ESRISHAPE from $(SourceDataset_ESRISHAPE_34)
- CSV2_1: CSV2 from $(SourceDataset_CSV2)
- CSV2_2: CSV2 from $(SourceDataset_CSV2_5)
- ESRISHAPE_5: ESRISHAPE from $(SourceDataset_ESRISHAPE_19)
- ESRISHAPE_6: ESRISHAPE from $(SourceDataset_ESRISHAPE_28)
- CSV2_3: CSV2 from $(SourceDataset_CSV2_4)
- ESRISHAPE_7: ESRISHAPE from $(SourceDataset_ESRISHAPE_30)
- ESRISHAPE_8: ESRISHAPE from $(SourceDataset_ESRISHAPE_31)
- ESRISHAPE_9: ESRISHAPE from $(SourceDataset_ESRISHAPE_32)

Writers:
- STL_1: STL to $(DestDataset_STL_3)
- ESRISHAPE_10: ESRISHAPE to $(DestDataset_ESRISHAPE)
- OGCKML_1: OGCKML to $(DestDataset_OGCKML_5) in EPSG:2157
- OBJ_1: OBJ to $(DestDataset_OBJ)
- IEPS_1: IEPS to $(DestDataset_IEPS)
- IEPS_2: IEPS to $(DestDataset_IEPS_3) in EPSG:2157
- FBX_1: FBX to $(DestDataset_FBX)
- GEOJSON_1: GEOJSON to $(DestDataset_GEOJSON)

Review Tiles Dublin Boundary 7x4km 1-2000 500m Tile (reader ESRISHAPE_8)
    attributes: left double, top double, right double, bottom double, id long
    -> AttributeFilter_5
    -> AttributeFilter_8
Print Tiles Dublin Boundary 7x4km 1-2000 1km Tile (reader ESRISHAPE_7)
    attributes: left double, top double, right double, bottom double, id long
    -> AttributeFilter_7
    -> AttributeFilter_10
Note: DTM
Junction_19
    -> Clipper_7 [CLIPPEE]
    -> Tile_out_DTM [CLIPPEE]
    -> SurfaceModeller_2 [POINTS/LINES]
Junction_4
    -> Junction_15
    -> Dissolver_2
    -> Clipper_13 [CLIPPER]
    -> EPS for bridges (writer IEPS_2)
Note: Grid/Tile
Junction_15
    -> tileClipper [CLIPPER]
    -> 3DForcer_6
    -> Bufferer
    -> Clipper_4 [CLIPPEE]
DLM_CORE_2019Q3_BUILDING_POLY (writer GEOJSON_1)
    attributes: GUID string, FORM_VALUE string, FUNC_VALUE string, ENG_NAME_VALUE string, STATUS_VALUE string, Z_ORDER_VALUE float, ADDR_GEO_CODE_1 string, ADDR_GEO_CODE_2 string, ADDR_NAT_POST_CODE string, WAY_SEG_VALUE string, BLD_NO_VALUE string, OBJECTID int
DLM_CORE_2019Q3_BUILDING_POLY (writer FBX_1)
Junction_12
    -> MeshSimplifier
MeshSimplifier
    AMOUNT = 0.5
    MODE = RELATIVE
    SIMPLIFIED -> Dublin Master_mesh simplified (writer OBJ_1)

Bookmark: Grids_Tiles
Print Tiles Dublin Boundary 7x4km 1-2000 1km Tile (reader ESRISHAPE_1)
    attributes: left double, top double, right double, bottom double, id long
    -> AttributeFilter

Bookmark: Tile filter
AttributeFilter
    ATTR_NAME = id
    ATTR_VALUES = <Empty>,<Missing>,<Null>,<Unfiltered>,2,3,5,6,7,8,9,10,11,12,13,14,15,16,17,18,19,20,21,22,23,24,26,27
    2 -> Junction_4 [off]
    3 -> Junction_4 [off]
    5 -> Junction_4 [off]
    6 -> Junction_4 [off]
    7 -> Junction_4 [off]
    8 -> Junction_4 [off]
    9 -> Junction_4 [off]
    10 -> Junction_4 [off]
    11 -> Junction_4 [off]
    12 -> Junction_4 [off]
    13 -> Junction_4 [off]
    14 -> Junction_4 [off]
    15 -> Junction_4 [off]
    16 -> Junction_4 [off]
    17 -> Junction_4 [off]
    18 -> Junction_4 [off]
    19 -> Junction_4
    20 -> Junction_4 [off]
    21 -> Junction_4 [off]
    22 -> Junction_4 [off]
    23 -> Junction_4 [off]
    24 -> Junction_4 [off]
    26 -> Junction_4 [off]
    27 -> Junction_4 [off]

Bookmark: Readers
DLM_CORE_2019Q3_BUILDING_POLY (reader FILEGDB_1)
    attributes: GUID text(114), FORM_VALUE text(120), FUNC_VALUE text(240), ENG_NAME_VALUE text(750), STATUS_VALUE text(120), Z_ORDER_VALUE double, ADDR_GEO_CODE_1 text(150), ADDR_GEO_CODE_2 text(150), ADDR_NAT_POST_CODE text(150), WAY_SEG_VALUE text(114), BLD_NO_VALUE text(750), OBJECTID objectid
    -> FeatureMerger [REQUESTOR]
DLM_CORE_ARTIFICIAL_POLY (reader FILEGDB_1)
    attributes: GUID text(114), FORM_VALUE text(120), FUNC_VALUE text(240), ENG_NAME_VALUE text(750), STATUS_VALUE text(120), Z_ORDER_VALUE double, OBJECTID objectid
    -> FeatureMerger_3 [REQUESTOR]
DLM_CORE_VEGETATION_POLY (reader FILEGDB_1)
    attributes: GUID text(114), FORM_VALUE text(120), FUNC_VALUE text(240), ENG_NAME_VALUE text(750), STATUS_VALUE text(120), Z_ORDER_VALUE double, ADDR_GEO_CODE_1 text(150), ADDR_GEO_CODE_2 text(150), ADDR_NAT_POST_CODE text(150), WAY_SEG_VALUE text(114), BLD_NO_VALUE text(750), OBJECTID objectid
    -> Return_specified_Core_Vegetation_Polys_for_extrusion
Repaired Features (reader ESRISHAPE_5)
    attributes: id long, repair_id char(5), repair_id2 char(7)
    -> Clip_Buildings [CLIPPEE]
Note: Dublin_Clipped_PointCloud 2017
LAS (reader LAS_1)
    -> Clipper_8 [CLIPPEE]
Note: LAS: LiDAR_2009_Hackathon_Dublin_2m_DTM [LAS]
LAS (reader LAS_2)
    -> Junction_19

Bookmark: Return_specified_Core_Vegetation_Polys_for_extrusion
Return_specified_Core_Vegetation_Polys_for_extrusion: AttributeFilter
    ATTR_NAME = OBJECTID
    ATTR_VALUES = <Empty>,<Missing>,<Null>,<Unfiltered>,6152,6155
    6152 -> Clip_Buildings [CLIPPEE]
    6155 -> Clip_Buildings [CLIPPEE]

Bookmark: Rounded Grid Cell Corners
AttributeFilter_5
    ATTR_NAME = id
    ATTR_VALUES = <Empty>,<Missing>,<Null>,<Unfiltered>,1,8,105,112
    1 -> Clipper_6 [CLIPPER]
    1 -> Clipper_3 [CLIPPER]
    8 -> Clipper_6 [CLIPPER]
    8 -> Clipper_3 [CLIPPER]
    105 -> Clipper_6 [CLIPPER]
    105 -> Clipper_3 [CLIPPER]
    112 -> Clipper_3 [CLIPPER]
    112 -> Clipper_6 [CLIPPER]
AttributeFilter_7
    ATTR_NAME = id
    ATTR_VALUES = <Empty>,<Missing>,<Null>,<Unfiltered>,1,4,25,28
    1 -> Clipper_3 [CLIPPEE]
    4 -> Clipper_3 [CLIPPEE]
    25 -> Clipper_3 [CLIPPEE]
    28 -> Clipper_3 [CLIPPEE]
Clipper_3
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    OUTSIDE -> Dissolver
Clipper_6
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> Dissolver
Dissolver
    ACCUM_INPUT_ATTRS = Use Attributes From One Feature
    CLEANING_TOLERANCE = Automatic
    CONNECT_Z_MODE = First Wins
    DEAGGREGATE_INPUT = Yes
    AREA -> Junction_4 [off]

Bookmark: Generate Rounded Model Boundary
AttributeFilter_8
    ATTR_NAME = id
    ATTR_VALUES = <Empty>,<Missing>,<Null>,<Unfiltered>,1,8,105,112
    1 -> Clipper_9 [CLIPPER]
    1 -> Clipper_11 [CLIPPER]
    8 -> Clipper_9 [CLIPPER]
    8 -> Clipper_11 [CLIPPER]
    105 -> Clipper_11 [CLIPPER]
    105 -> Clipper_9 [CLIPPER]
    112 -> Clipper_9 [CLIPPER]
    112 -> Clipper_11 [CLIPPER]
AttributeFilter_10
    ATTR_NAME = id
    ATTR_VALUES = <Empty>,<Missing>,<Null>,<Unfiltered>,1,4,25,28
    1 -> Clipper_9 [CLIPPEE]
    4 -> Clipper_9 [CLIPPEE]
    25 -> Clipper_9 [CLIPPEE]
    28 -> Clipper_9 [CLIPPEE]
Clipper_9
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    OUTSIDE -> Dissolver_2
Junction
    -> Clipper_11 [CLIPPEE]
    -> Dublin Model Outline (writer IEPS_1)
Clipper_11
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> Dissolver_2
Dissolver_2
    ACCUM_INPUT_ATTRS = Use Attributes From One Feature
    CLEANING_TOLERANCE = Automatic
    CONNECT_Z_MODE = First Wins
    DEAGGREGATE_INPUT = Yes
    AREA -> Dublin Model Outline (writer IEPS_1) [off]
    AREA -> Clipper_12 [CLIPPER]
    AREA -> Junction_15 [off]
Dublin Model Outline (writer IEPS_1)
    attributes: id number(11,0), _clipped char(200), left char(200), top char(200), right char(200), bottom char(200), _fme_no_clipper char(200)

Bookmark: Outputs
Note: .stl writer
Print 0.6.2 Tile 14 DTM Unthinned Surface Tolerance 0.165 Aggregate No river no rail (writer STL_1)
KML (writer OGCKML_1)
Note: .obj writer
Dublin Master_mesh simplified (writer OBJ_1)
Note: Output inspector
Inspector

Bookmark: Corner Circles
Circle (reader ESRISHAPE_9)
    attributes: id long
    -> Clipper_6 [CLIPPEE]
    -> Junction

Bookmark: Clip features with buffered model boundary
Note: Add buffer around boundary
Bufferer
    ANGLE = 22.5
    CAP_STYLE = None
    CORNER_STYLE = Round
    MODE = AREA
    OFFSET = 125
    BUFFERED -> Clip_Buildings [CLIPPER]
    BUFFERED -> Tile_out_DTM [CLIPPER]
Note: Clip features with buffered model boundary
Clip_Buildings: Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> GeometryExtractor_2
    INSIDE -> DLM_CORE_2019Q3_BUILDING_POLY (writer FBX_1)
    INSIDE -> DLM_CORE_2019Q3_BUILDING_POLY (writer GEOJSON_1)

Bookmark: Surface Drape
Note: DTM clipped by tile and buffered tile
Tile_out_DTM: Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> SurfaceModeller [POINTS/LINES]
Note: Build surface model / Drape clipping boundary / Output triangles / https://knowledge.safe.com/articles/1310/how-to-clip-tin-surfaces.html
SurfaceModeller
    CONTOUR_DIMENSION = 3
    CONTOUR_INTERVAL = 100.0
    DRAPE_TYPE = MODEL
    ELEV_ATTR = _elevation
    IGNORE_INPUT_ON_INTERVAL = Perturb Input Points On Contour Interval
    INTERPOLATION_TYPE = AUTO
    NODATA_VALUE = -32767.0
    TOLERANCE = 0.165
    X_SPACING = 100.0
    Y_SPACING = 100.0
    DRAPED_FEATURES -> Clipper_5 [CLIPPER]
    TRIANGLES -> Clipper_5 [CLIPPEE]
Note: Clip triangles by boundary
Clipper_5
    BOUNDARY_CASES = Treat as Outside
    CLIP_TYPE = Multiple Clippers
    CREATE_AGGREGATES = Yes
    MERGE_ATTRS = No
    PRESERVE_CLIPPEE_EXTENTS = No
    INSIDE -> FaceReplacer_3
    CLIPPED_INSIDE -> FaceReplacer_3

Bookmark: Base
3DForcer_6
    KEEPZVAL = No
    ZVALATTR = -3
    -> Extruder_4
Extruder_4
    DIRECTION = Vertical
    DISTANCE = 0.5
    EXTRUDED -> Junction_17

Bookmark: Feature Merging
Note: Base
Junction_17
    -> Junction_10
Note: Extrusion to below surface
Junction_14
    -> Junction_10 [off]
Note: Extrusion z-min -> median
Junction_6
    -> Junction_10
Note: Terrain
Junction_9
    -> Junction_10
Note: Water
Junction_8
    -> Junction_10
Junction_10
    -> 3DRotator
Note: Rotate to correct orientation
3DRotator
    ANGLE = -90
    AXIS_CHOICE = X Axis
    ROTATED -> Junction_12
    ROTATED -> Inspector

Bookmark: Filter out problem building polys
Note: Repair List
CSV (reader CSV2_1)
    attributes: repair_id2 string, repair_id string, OBJECT ID string, Notes string
    -> FeatureMerger [SUPPLIER]
FeatureMerger
    ATTR_ACCUM_MODE = Merge Supplier
    ATTR_CONFLICT_RES = Use Requestor
    IGNORE_NULLS = No
    JOIN_KEYS = @Value(OBJECTID) @Value(OBJECT ID) AUTO
    MERGE_TYPE = Attributes Only
    PROCESS_DUPS = NO
    REJECT_NULL_MISSING_KEYS = No
    SUPPLIERS_FIRST = No
    UNMERGED_REQUESTOR -> Clip_Buildings [CLIPPEE]

Bookmark: Return specified Core Artificial Polys for extrusion
Core Artificial Poly Attribute Filter (reader CSV2_3)
    attributes: OBJECTID string
    -> FeatureMerger_3 [SUPPLIER]
FeatureMerger_3
    ATTR_ACCUM_MODE = Merge Supplier
    ATTR_CONFLICT_RES = Use Requestor
    IGNORE_NULLS = No
    JOIN_KEYS = @Value(OBJECTID) @Value(OBJECTID) AUTO
    MERGE_TYPE = Attributes Only
    PROCESS_DUPS = NO
    REJECT_NULL_MISSING_KEYS = No
    SUPPLIERS_FIRST = No
    MERGED -> Clip_Buildings [CLIPPEE]

Bookmark: PointCloud Statistics
Note: Geometry stored for extruding buildings in subsequent steps.
GeometryExtractor_2
    ATTR = _geometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> Clipper_8 [CLIPPER]
    -> Clipper_7 [CLIPPER]
Note: Clip point cloud with building geometry
Clipper_8
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> PointCloudStatisticsCalculator_2
PointCloudStatisticsCalculator_2
    POINT_COMPONENTS = "z       MEDIAN  intensity        "
    -> Aggregator_2
Clipper_7
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> PointCloudStatisticsCalculator_3
PointCloudStatisticsCalculator_3
    POINT_COMPONENTS = "z MIN        intensity        "
    -> Aggregator_2
Aggregator_2
    ACCUM_ATTRS_NAME = Merge Incoming Attributes
    GROUP_BY = repair_id2 GUID repair_id
    MODE = Attributes Only
    SEP = ,
    AGGREGATE -> GeometryReplacer
Note: Replace _geometry attribute
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> tileClipper [CLIPPEE]
Note: Clip with tile
tileClipper: Clipper
    ATTR_ACCUM_MODE = Merge Clipper
    ATTR_CONFLICT_RES = Use Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> AttributeManager

Bookmark: z.median overrides
AttributeManager
    ATTR_TABLE = SET_TO z.median = FME_CONDITIONAL:DEFAULT_VALUE'_FME_NO_OP_'BOOL_OP;OR;COMPOSITE_TEST;1;TEST @Value(repair_id) = D3.01'21.22'BOOL_OP;OR;COMPOSITE_TEST;1;TEST @Value(OBJECTID) = 44408'27.18'BOOL_OP;OR;COMPOSITE_TEST;1;TEST @Value(OBJECTID) = 44429'27.18'BOOL_OP;OR;COMPOSITE_TEST;1;TEST @Value(OBJECTID) = 44432'27.18'BOOL_OP;OR;COMPOSITE_TEST;1;TEST @Value(OBJECTID) = 43103'25'BOOL_OP;OR;COMPOSITE_TEST;1;TEST @Value(repair_id) = C2.4B'32'BOOL_OP;OR;COMPOSITE_TEST;1;TEST @Value(OBJECTID) = 43096'50'BOOL_OP;OR;COMPOSITE_TEST;1;TEST @Value(repair_id) = B2.1'25'BOOL_OP;OR;COMPOSITE_TEST;1;TEST @Value(repair_id) = B2.3'25'BOOL_OP;OR;COMPOSITE_TEST;1;TEST @Value(repair_id) = B2.5'34.25'BOOL_OP;OR;COMPOSITE_TEST;1;TEST @Value(repair_id) = B3.7C'34.25'BOOL_OP;OR;COMPOSITE_TEST;1;TEST @Value(repair_id) = B316B'50'BOOL_OP;OR;COMPOSITE_TEST;1;TEST @Value(repair_id) = B318A'50'BOOL_OP;OR;COMPOSITE_TEST;1;TEST @Value(repair_id) = B318C'60'BOOL_OP;OR;COMPOSITE_TEST;1;TEST @Value(repair_id) = B318D'60'BOOL_OP;OR;COMPOSITE_TEST;1;TEST @Value(repair_id) = B318E'50'BOOL_OP;OR;COMPOSITE_TEST;1;TEST @Value(repair_id) = D3.24'18'BOOL_OP;OR;COMPOSITE_TEST;1;TEST @Value(OBJECTID) = 111839'36'BOOL_OP;OR;COMPOSITE_TEST;1;TEST @Value(OBJECTID) = 111938'27'BOOL_OP;OR;COMPOSITE_TEST;1;TEST @Value(repair_id) = D3.35'30'BOOL_OP;OR;COMPOSITE_TEST;1;TEST @Value(repair_id) = D3.38A'30'BOOL_OP;OR;COMPOSITE_TEST;1;TEST @Value(OBJECTID) = 205'3'BOOL_OP;OR;COMPOSITE_TEST;1;TEST @Value(repair_id) = D2.1B'14.46'BOOL_OP;OR;COMPOSITE_TEST;1;TEST @Value(repair_id) = D2.2A'26.19'BOOL_OP;OR;COMPOSITE_TEST;1;TEST @Value(repair_id) = D2.24B'33'BOOL_OP;OR;COMPOSITE_TEST;1;TEST @Value(OBJECTID) = 105179'40'BOOL_OP;OR;COMPOSITE_TEST;1;TEST @Value(repair_id) = D2.Br1'3'BOOL_OP;OR;COMPOSITE_TEST;1;TEST @Value(repair_id) = E2.13C'26'BOOL_OP;OR;COMPOSITE_TEST;1;TEST @Value(repair_id) = E2.21B'26.39'BOOL_OP;OR;COMPOSITE_TEST;1;TEST @Value(repair_id) = E2.21A'24'BOOL_OP;OR;COMPOSITE_TEST;1;TEST @Value(repair_id) = E2.21D'30'BOOL_OP;OR;COMPOSITE_TEST;1;TEST @Value(repair_id) = E2.21C'32'BOOL_OP;OR;COMPOSITE_TEST;1;TEST @Value(repair_id) = E3.1A'25'BOOL_OP;OR;COMPOSITE_TEST;1;TEST @Value(repair_id) = E3.1B'14'BOOL_OP;OR;COMPOSITE_TEST;1;TEST @Value(repair_id) = E3.2'50'BOOL_OP;OR;COMPOSITE_TEST;1;TEST @Value(repair_id) = E3.5'27'BOOL_OP;OR;COMPOSITE_TEST;1;TEST @Value(OBJECTID) = 96860'52'BOOL_OP;OR;COMPOSITE_TEST;1;TEST @Value(OBJECTID) = 96859'30'BOOL_OP;OR;COMPOSITE_TEST;1;TEST @Value(repair_id) = E3.10A'27'BOOL_OP;OR;COMPOSITE_TEST;1;TEST @Value(repair_id) = F2.1'25'BOOL_OP;OR;COMPOSITE_TEST;1;TEST @Value(repair_id) = F2.2'25'BOOL_OP;OR;COMPOSITE_TEST;1;TEST @Value(repair_id) = F2.4'33'BOOL_OP;OR;COMPOSITE_TEST;1;TEST @Value(repair_id) = F2.12'33'BOOL_OP;OR;COMPOSITE_TEST;1;TEST @Value(repair_id) = W1'2'BOOL_OP;OR;COMPOSITE_TEST;1;TEST @Value(repair_id) = F3.7A'28'BOOL_OP;OR;COMPOSITE_TEST;1;TEST @Value(repair_id) = F3.9'38.84'BOOL_OP;OR;COMPOSITE_TEST;1;TEST @Value(repair_id) = F3.10F'38.84'BOOL_OP;OR;COMPOSITE_TEST;1;TEST @Value(repair_id) = F3.10E'8'BOOL_OP;OR;COMPOSITE_TEST;1;TEST @Value(repair_id) = F3.10D'32'BOOL_OP;OR;COMPOSITE_TEST;1;TEST @Value(repair_id) = F3.10A'59'BOOL_OP;OR;COMPOSITE_TEST;1;TEST @Value(repair_id) = F3.10C'74'BOOL_OP;OR;COMPOSITE_TEST;1;TEST @Value(repair_id) = F3.10B'77'BOOL_OP;OR;COMPOSITE_TEST;1;TEST @Value(repair_id) = F3.11'11'BOOL_OP;OR;COMPOSITE_TEST;1;TEST @Value(repair_id) = F3.12B'28'BOOL_OP;OR;COMPOSITE_TEST;1;TEST @Value(repair_id) = F4.4'12'BOOL_OP;OR;COMPOSITE_TEST;1;TEST @Value(repair_id) = F4.6'32'BOOL_OP;OR;COMPOSITE_TEST;1;TEST @Value(repair_id) = F4.8B'26'BOOL_OP;OR;COMPOSITE_TEST;1;TEST @Value(OBJECTID) = 134461'32'BOOL_OP;OR;COMPOSITE_TEST;1;TEST @Value(repair_id) = E4.21B'40'BOOL_OP;OR;COMPOSITE_TEST;1;TEST @Value(repair_id) = E4.31B'40'BOOL_OP;OR;COMPOSITE_TEST;1;TEST @Value(repair_id) = E4.17B'24'BOOL_OP;OR;COMPOSITE_TEST;1;TEST @Value(repair_id) = E4.17A'24'BOOL_OP;OR;COMPOSITE_TEST;1;TEST @Value(repair_id) = D4.8'31'BOOL_OP;OR;COMPOSITE_TEST;1;TEST @Value(repair_id) = D4.33'31'BOOL_OP;OR;COMPOSITE_TEST;1;TEST @Value(repair_id) = D4.13A'35'BOOL_OP;OR;COMPOSITE_TEST;1;TEST @Value(repair_id) = D4.32'43'BOOL_OP;OR;COMPOSITE_TEST;1;TEST @Value(repair_id) = C4.1'31'BOOL_OP;OR;COMPOSITE_TEST;1;TEST @Value(OBJECTID) = 42349'33'BOOL_OP;OR;COMPOSITE_TEST;1;TEST @Value(OBJECTID) = 38090'33'BOOL_OP;OR;COMPOSITE_TEST;1;TEST @Value(OBJECTID) = 38086'28'BOOL_OP;OR;COMPOSITE_TEST;1;TEST @Value(OBJECTID) = 42353'28'BOOL_OP;OR;COMPOSITE_TEST;1;TEST @Value(OBJECTID) = 38081'24'BOOL_OP;OR;COMPOSITE_TEST;1;TEST @Value(repair_id) = C4.5B'39'BOOL_OP;OR;COMPOSITE_TEST;1;TEST @Value(repair_id) = B4.2'28'BOOL_OP;OR;COMPOSITE_TEST;1;TEST @Value(repair_id) = B4.5A'32'BOOL_OP;OR;COMPOSITE_TEST;1;TEST @Value(repair_id) = B4.5D'32'BOOL_OP;OR;COMPOSITE_TEST;1;TEST @Value(repair_id) = B4.8'38'BOOL_OP;OR;COMPOSITE_TEST;1;TEST @Value(OBJECTID) = 156643'45'BOOL_OP;OR;COMPOSITE_TEST;1;TEST @Value(repair_id) = B1.3A'50'BOOL_OP;OR;COMPOSITE_TEST;1;TEST @Value(repair_id) = B1.3C'38'BOOL_OP;OR;COMPOSITE_TEST;1;TEST @Value(repair_id) = B1.4'44'BOOL_OP;OR;COMPOSITE_TEST;1;TEST @Value(repair_id) = C1.3B'50'BOOL_OP;OR;COMPOSITE_TEST;1;TEST @Value(repair_id) = C1.9Q'45'BOOL_OP;OR;COMPOSITE_TEST;1;TEST @Value(repair_id) = C1.9R'45'BOOL_OP;OR;COMPOSITE_TEST;1;TEST @Value(repair_id) = C1.9S'45'BOOL_OP;OR;COMPOSITE_TEST;1;TEST @Value(repair_id) = C1.9T'45'BOOL_OP;OR;COMPOSITE_TEST;1;TEST @Value(repair_id) = D1.1B'45'BOOL_OP;OR;COMPOSITE_TEST;1;TEST @Value(repair_id) = F1.4A'15'BOOL_OP;OR;COMPOSITE_TEST;1;TEST @Value(repair_id) = G2.13B'30'BOOL_OP;OR;COMPOSITE_TEST;1;TEST @Value(repair_id) = G2.13D'45'BOOL_OP;OR;COMPOSITE_TEST;1;TEST @Value(repair_id) = G2.13E'45'BOOL_OP;OR;COMPOSITE_TEST;1;TEST @Value(repair_id) = G3.5A'20'BOOL_OP;OR;COMPOSITE_TEST;1;TEST @Value(repair_id) = A2.4D'55'BOOL_OP;OR;COMPOSITE_TEST;1;TEST @Value(repair_id) = A3.4D'40'BOOL_OP;OR;COMPOSITE_TEST;1;TEST @Value(repair_id) = A3.5'23'BOOL_OP;OR;COMPOSITE_TEST;1;TEST @Value(repair_id) = A3.6A'42'BOOL_OP;OR;COMPOSITE_TEST;1;TEST @Value(repair_id) = heart'29.25'FME_NUM_CONDITIONS98___
    -> 3DForcer_8
    -> 3DForcer_4
    -> 3DForcer_3

Bookmark: Building Extrusion
Note: 2D -> 3D
3DForcer_8
    KEEPZVAL = No
    ZVALATTR = -5
    -> Extruder_7
Note: Extrude to median heights
Extruder_7
    DIRECTION = Vertical
    DISTANCE = @Value(z.median)-(-5)
    EXTRUDED -> Junction_13
Note: Output
Junction_13
    -> Junction_14

Bookmark: Extrusion z.min -> z.median
Note: 2D -> 3D
3DForcer_3
    KEEPZVAL = No
    ZVALATTR = @Value(z.min)
    -> Extruder_3
Note: Extrude to median heights
Extruder_3
    DIRECTION = Vertical
    DISTANCE = @Value(z.median)-@Value(z.min)
    EXTRUDED -> Junction_11
Note: Output
Junction_11
    -> Junction_6

Bookmark: Prep for KML
Note: 2D -> 3D
3DForcer_4
    KEEPZVAL = No
    ZVALATTR = @Value(z.median)
    -> KMLPropertySetter
KMLPropertySetter
    ADD_ATTR_TABLE = Yes
    ALTITUDE_MODE = Absolute
    ATTR_TABLE_TITLE = Attributes
    CONTENT_TYPE = Text
    EXTRUDE = Yes
    GEOM_TYPE = Vector
    NAME = <auto>
    SUMMARY = <none>
    TESSELATE = Yes
    VISIBILITY = Yes
    -> KML (writer OGCKML_1) [off]

Bookmark: Water Surface
Note: Prime2 Water Features
DLM_CORE_WATER_POLY (reader FILEGDB_1)
    attributes: GUID text(114), FORM_VALUE text(120), FUNC_VALUE text(240), ENG_NAME_VALUE text(750), STATUS_VALUE text(120), Z_ORDER_VALUE double, ADDR_GEO_CODE_1 text(150), ADDR_GEO_CODE_2 text(150), ADDR_NAT_POST_CODE text(150), WAY_SEG_VALUE text(114), BLD_NO_VALUE text(750), OBJECTID objectid
    -> FeatureMerger_2 [REQUESTOR]
Sea (reader ESRISHAPE_6)
    attributes: id long, repair_id2 char(7)
    -> Clipper [CLIPPEE]
    -> Clipper_12 [CLIPPEE]
CSV (reader CSV2_2)
    attributes: OBJECTID string, Z_ORDER_VALUE string
    -> FeatureMerger_2 [SUPPLIER]
FeatureMerger_2
    ATTR_ACCUM_MODE = Merge Supplier
    ATTR_CONFLICT_RES = Use Requestor
    IGNORE_NULLS = No
    JOIN_KEYS = @Value(OBJECTID) @Value(OBJECTID) AUTO
    MERGE_TYPE = Attributes Only
    PROCESS_DUPS = NO
    REJECT_NULL_MISSING_KEYS = No
    SUPPLIERS_FIRST = No
    UNMERGED_REQUESTOR -> AttributeFilter_3
    UNMERGED_REQUESTOR -> Clipper_12 [CLIPPEE]
    UNMERGED_REQUESTOR -> AttributeFilter_11
Note: Filter out all water features that lie under bridges etc.
AttributeFilter_3
    ATTR_NAME = Z_ORDER_VALUE
    ATTR_VALUES = <Empty>,<Missing>,<Null>,<Unfiltered>,-1
    <UNFILTERED> -> Clipper [CLIPPEE]
Note: Bridges missing in Prime2
Repaired Bridges (reader ESRISHAPE_4)
    attributes: id long
    -> Clipper [CLIPPER]
    -> Clipper_13 [CLIPPEE]
Note: Filter out bridges missing in Prime2
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    OUTSIDE -> SurfaceModeller_2 [DRAPE_FEATURES]
SurfaceModeller_2
    CONTOUR_DIMENSION = 3
    CONTOUR_INTERVAL = 100.0
    DRAPE_TYPE = MODEL
    ELEV_ATTR = _elevation
    IGNORE_INPUT_ON_INTERVAL = Perturb Input Points On Contour Interval
    INTERPOLATION_TYPE = AUTO
    NODATA_VALUE = -32767.0
    TOLERANCE = 40
    X_SPACING = 100.0
    Y_SPACING = 100.0
    DRAPED_FEATURES -> GeometryExtractor_3
GeometryExtractor_3
    ATTR = _watergeometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> BoundsExtractor_2
BoundsExtractor_2
    XMAX = _xmax
    XMIN = _xmin
    YMAX = _ymax
    YMIN = _ymin
    ZMAX = _zmax
    ZMIN = _zmin
    -> StatisticsCalculator
StatisticsCalculator
    COMPUTE_HISTOGRAM = NO
    COUNT_ATTR = _count
    MAX_ATTR = _max
    MEAN_ATTR = _mean
    MIN_ATTR = _min
    PREPEND_ATTR_NAME_CHOICE = For multiple results only
    STATS_ATTRS = _zmin
    SUM_ATTR = _sum
    COMPLETE -> GeometryReplacer_2
GeometryReplacer_2
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_watergeometry)
    SRS_AXIS_ORDER_DISPLAY = Automatic
    -> Clipper_4 [CLIPPER]
Note: Tile out water features
Clipper_4
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> 3DForcer_5
    OUTSIDE -> SurfaceModeller [DRAPE_FEATURES]
3DForcer_5
    KEEPZVAL = No
    ZVALATTR = @Value(_zmin)
    -> AttributeFilter_9
AttributeFilter_9
    ATTR_NAME = OBJECTID
    ATTR_VALUES = <Empty>,<Missing>,<Null>,<Unfiltered>,259,437,137,453,90,96,148
    <MISSING> -> Offsetter
    <UNFILTERED> -> Offsetter
    259 -> Offsetter_2
    437 -> Offsetter_3
    137 -> Offsetter_4
    453 -> Offsetter_5
    90 -> Offsetter_6
    96 -> Offsetter_7
    148 -> Offsetter_8
Offsetter
    MODE = Cartesian Coordinate
    XOFF = 0
    YOFF = 0
    ZOFF = -1
    OFFSET -> Extruder_6
Extruder_6
    DIRECTION = Vertical
    DISTANCE = -0.5
    EXTRUDED -> Junction_2
Offsetter_2
    MODE = Cartesian Coordinate
    XOFF = 0
    YOFF = 0
    ZOFF = 0
    OFFSET -> Extruder_2
Extruder_2
    DIRECTION = Vertical
    DISTANCE = -0.5
    EXTRUDED -> Junction_2
Offsetter_3
    MODE = Cartesian Coordinate
    XOFF = 0
    YOFF = 0
    ZOFF = -2.5
    OFFSET -> Extruder_9
Extruder_9
    DIRECTION = Vertical
    DISTANCE = -0.5
    EXTRUDED -> Junction_2
Offsetter_4
    MODE = Cartesian Coordinate
    XOFF = 0
    YOFF = 0
    ZOFF = 0
    OFFSET -> Extruder_8
Extruder_8
    DIRECTION = Vertical
    DISTANCE = -0.5
    EXTRUDED -> Junction_2
Offsetter_5
    MODE = Cartesian Coordinate
    XOFF = 0
    YOFF = 0
    ZOFF = -3.25
    OFFSET -> Extruder_18
Extruder_18
    DIRECTION = Vertical
    DISTANCE = -0.5
    EXTRUDED -> Junction_2
Offsetter_6
    MODE = Cartesian Coordinate
    XOFF = 0
    YOFF = 0
    ZOFF = -3.25
    OFFSET -> Extruder_19
Extruder_19
    DIRECTION = Vertical
    DISTANCE = -0.5
    EXTRUDED -> Junction_2
Offsetter_7
    MODE = Cartesian Coordinate
    XOFF = 0
    YOFF = 0
    ZOFF = 2.5
    OFFSET -> Extruder_20
Extruder_20
    DIRECTION = Vertical
    DISTANCE = -0.5
    EXTRUDED -> Junction_2
Offsetter_8
    MODE = Cartesian Coordinate
    XOFF = 0
    YOFF = 0
    ZOFF = -3.7
    OFFSET -> Extruder_21
Extruder_21
    DIRECTION = Vertical
    DISTANCE = -0.5
    EXTRUDED -> Junction_2
Junction_2
    -> Junction_8 [off]

Bookmark: Water Feature Outlines .eps
Clipper_12
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> Dissolver_3
Dissolver_3
    ACCUM_INPUT_ATTRS = Use Attributes From One Feature
    CLEANING_TOLERANCE = Automatic
    CONNECT_Z_MODE = First Wins
    DEAGGREGATE_INPUT = Yes
    AREA -> EPS for water features (writer IEPS_2) [off]
Boundary Dublin 7x4km 1-2000 (reader ESRISHAPE_3)
    attributes: left double, top double, right double, bottom double, id long
    -> EPS for water features (writer IEPS_2)
EPS for water features (writer IEPS_2)
    attributes: left number(31,15), top number(31,15), right number(31,15), bottom number(31,15), id number(11,0), GUID char(114), FORM_VALUE char(120), FUNC_VALUE char(240), ENG_NAME_VALUE char(750), STATUS_VALUE char(120), Z_ORDER_VALUE number(31,15), ADDR_GEO_CODE_1 char(150), ADDR_GEO_CODE_2 char(150), ADDR_NAT_POST_CODE char(150), WAY_SEG_VALUE char(114), BLD_NO_VALUE char(750), OBJECTID number(11,0), repair_id2 char(7), _clipped char(200)

Bookmark: Bridges .eps
Note: Filter out all water features that lie under bridges etc.
AttributeFilter_11
    ATTR_NAME = Z_ORDER_VALUE
    ATTR_VALUES = <Empty>,<Missing>,<Null>,<Unfiltered>,-1
    -1 -> Clipper_13 [CLIPPEE]
Clipper_13
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> EPS for bridges (writer IEPS_2)
EPS for bridges (writer IEPS_2)
    attributes: id number(11,0), GUID char(114), FORM_VALUE char(120), FUNC_VALUE char(240), ENG_NAME_VALUE char(750), STATUS_VALUE char(120), Z_ORDER_VALUE number(31,15), ADDR_GEO_CODE_1 char(150), ADDR_GEO_CODE_2 char(150), ADDR_NAT_POST_CODE char(150), WAY_SEG_VALUE char(114), BLD_NO_VALUE char(750), OBJECTID number(11,0), _clipped char(200), left char(200), top char(200), right char(200), bottom char(200), _fme_no_clipper char(200)

Bookmark: Taksahi Flow creates base by creating side and bottom faces from terrain surface
Note: Replace polygons with faces
FaceReplacer_3
    CHECK_PLANARITY = No
    PLANARITY_TOLERANCE = 0.0
    -> AggregateFilter
AggregateFilter
    AGGREGATE -> AttributeCreator_3
    NOT_AGGREGATE -> GeometryFilter
GeometryFilter
    BREAK_AGG = No
    GEOM_PORT_NAMES = Surface
    SURFACE -> BoundsExtractor
    <UNFILTERED> -> AttributeCreator_3
BoundsExtractor
    ZMAX = __ssc.zmax
    ZMIN = __ssc.zmin
    -> AttributeCreator
AttributeCreator
    ATTR_TABLE:
      SET_TO __ssc.elevation = $(ELEVATION)
      SET_TO __ssc.flag = FME_CONDITIONAL:DEFAULT_VALUE'0'BOOL_OP;OR;COMPOSITE_TEST;<Unused>;TEST $(ELEVATION) < @Value(__ssc.zmin)'-1'BOOL_OP;OR;COMPOSITE_TEST;<Unused>;TEST @Value(__ssc.zmax) < $(ELEVATION)'1'FME_NUM_CONDITIONS3___
    -> Tester
Tester
    BOOL_OP = OR
    COMPOSITE_TEST = 1
    TEST_CLAUSE = TEST @Value(__ssc.flag) != 0
    TEST_MODE = TEST
    PASSED -> Counter
    FAILED -> AttributeCreator_2
Counter
    CNT_ATTR = __ssc.id
    DOMAIN = counter_id
    SCOPE = Local
    START = 0
    -> PythonCaller
    -> Tester_2
Tester_2
    BOOL_OP = OR
    TEST_CLAUSE = TEST @Value(__ssc.flag) < 0
    TEST_MODE = Automatic
    PASSED -> Tester_3_PASSED
    FAILED -> Orientor
Note: Top
Tester_3_PASSED: Junction
    -> Top_2
Orientor
    FLIP_APPEARANCES_CHOICE = Yes
    KIND = REVERSE
    ORIENTED -> Tester_3_FAILED
Note: Bottom
Tester_3_FAILED: Junction
    -> Bottom_2 [off]
PythonCaller
    NEW_ATTRIBUTES = __ssc.id
    PYTHONSOURCE:
      # 2016-09-16, Takashi Iijima, Original Implementation

      import fme
      import fmeobjects

      class OutershellChopper(object):
          def input(self, feature):
              flag = int(feature.getAttribute('__ssc.flag'))
              self.chopped = []
              self.chop(feature.getGeometry())
              segs = {}
              for line in self.chopped:
                  coords = sorted([p.getXYZ() for p in line.getPoints()])
                  segs.setdefault((coords[0], coords[1]), []).append(line)
              for line in [s[0] for s in segs.values() if len(s) == 1]:
                  if flag < 0:
                      line.reverse()
                  feature.setGeometry(line)
                  self.pyoutput(feature)

          def chop(self, surface):
              if isinstance(surface, fmeobjects.FMEFace):
                  self.chopped += surface.getAsWireFrame()
              elif isinstance(surface, fmeobjects.FMEMesh):
                  self.chopped += surface.getAsWireFrame()
              elif isinstance(surface, fmeobjects.FMERectangleFace):
                  self.chop(surface.getAsFaceCopy())
              elif isinstance(surface, fmeobjects.FMETriangleFan):
                  for i in range(surface.numParts()):
                      self.chop(surface.getAsFaceAt(i))
              elif isinstance(surface, fmeobjects.FMETriangleStrip):
                  for i in range(surface.numParts()):
                      self.chop(surface.getAsFaceAt(i))
              elif isinstance(surface, fmeobjects.FMECompositeSurface):
                  for i in range(surface.numParts()):
                      self.chop(surface.getPartAt(i))
    PYTHONSYMBOL = OutershellChopper
    -> LineJoiner
LineJoiner
    ACCUM_ATTRS_NAME = Get Attributes From One Representative Feature
    BREAK = no
    CONSIDER_NODE_ELEVATION = yes
    GROUP_BY = __ssc.id
    LINES_AS_SEGMENTS = Yes
    PRESERVE = yes
    TOPOLOGY = End noded
    LINE -> Counter_2
Counter_2
    CNT_ATTR = __ssc.part_id
    DOMAIN = counter_part_id
    SCOPE = Local
    START = 0
    -> PathSplitter
PathSplitter
    -> PythonCaller_2
PythonCaller_2
    NEW_ATTRIBUTES = __ssc.type
    PYTHONSOURCE:
      # 2016-09-16: Takashi Iijima, Original Implementation

      import fme
      import fmeobjects
      class BRepSolidBoundaryCreator(object):
          def __init__(self):
              self.wallFaces = {}
              self.planarBoundaries = {}
              self.prevId = None
              self.feature = None

          def input(self, feature):
              id = feature.getAttribute('__ssc.id')
              if id != self.prevId:
                  self.outputSurface()
                  self.wallFaces = {}
                  self.planarBoundaries = {}
                  self.prevId = id
              partId = feature.getAttribute('__ssc.part_id')
              if partId not in self.wallFaces:
                  self.wallFaces[partId] = []
                  self.planarBoundaries[partId] = []
              v0 = feature.getCoordinate(0)
              v1 = feature.getCoordinate(1)
              if v0[0] != v1[0] or v0[1] != v1[1]:
                  z = float(feature.getAttribute('__ssc.elevation'))
                  v2 = (v1[0], v1[1], z)
                  v3 = (v0[0], v0[1], z)
                  boundary = fmeobjects.FMELine([v0, v1, v2, v3, v0])
                  self.wallFaces[partId].append(fmeobjects.FMEFace(boundary, fmeobjects.FME_CLOSE_3D_AVERAGE_MODE))
                  self.planarBoundaries[partId].append(v2)
                  self.feature = feature

          def close(self):
              self.outputSurface()

          def outputSurface(self):
              for partId in sorted(self.wallFaces.keys()):
                  wallFaces = self.wallFaces[partId]
                  planarBoundaries = self.planarBoundaries[partId]
                  if wallFaces:
                      sidewall = fmeobjects.FMECompositeSurface()
                      for face in wallFaces:
                          sidewall.appendPart(face)
                      self.feature.setGeometry(sidewall)
                      self.feature.setAttribute('__ssc.type', 'side')
                      self.pyoutput(self.feature)

                      planarBoundaries.append(planarBoundaries[0])
                      planar = fmeobjects.FMEPolygon(fmeobjects.FMELine(planarBoundaries))
                      self.feature.setGeometry(planar)
                      self.feature.setAttribute('__ssc.type', 'planar')
                      self.pyoutput(self.feature)
    PYTHONSYMBOL = BRepSolidBoundaryCreator
    -> Tester_3
Tester_3
    BOOL_OP = OR
    TEST_CLAUSE = TEST @Value(__ssc.type) = side
    TEST_MODE = Automatic
    PASSED -> Junction_5
    FAILED -> DonutBuilder [off]
Note: Sides
Junction_5
    -> Aggregator [off]
DonutBuilder
    ALLOW_CYCLES = No
    CONNECT_Z_MODE = First Wins
    DROP = yes
    GROUP_BY = __ssc.id
    AREA -> FaceReplacer
FaceReplacer
    ANGULAR_TOLERANCE_CHOICE = Automatic
    THICKNESS_TOLERANCE_CHOICE = Automatic
    -> Tester_4
Tester_4
    BOOL_OP = OR
    TEST_CLAUSE = TEST 0 < @Value(__ssc.flag)
    TEST_MODE = Automatic
    PASSED -> Top_2
    FAILED -> Bottom_2
Note: Tester 2: Passed
Top_2: Junction
    -> Aggregator
Note: Orientor: Oriented
Bottom_2: Junction
    -> Aggregator
Note: Output
Junction_7
    -> Junction_9 [off]
AttributeCreator_2
    ATTR_TABLE = SET_TO _rejected_reason = specified elevation is within zmin and zmax of seed surface
    -> Junction_3
AttributeCreator_3
    ATTR_TABLE = SET_TO _rejected_reason = unsupported geometry type
    -> Junction_3
Junction_3
    -> Inspector_2
Note: Rejected
Inspector_2

Bookmark: Terrain Solid Model
Aggregator
    ACCUM_ATTRS_NAME = Use Attributes From One Feature
    AGGREGATE_TYPE = Homogeneous Collection (If Possible)
    MODE = Geometry - Assemble One Level
    ORDERED = No
    SEP = ,
    AGGREGATE -> GeometryCoercer_3
GeometryCoercer_3
    GQUERY:
      for $geom in //geometry
      where $geom/count(parent::geometry) = 0
      return number($geom/@fme_id)
    KIND = fme_brep_solid
    COERCED -> Junction_7
