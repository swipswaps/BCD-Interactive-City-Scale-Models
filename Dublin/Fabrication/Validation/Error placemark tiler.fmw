FME workspace Error placemark tiler.fmw

Parameters:
- SourceDataset_ESRISHAPE = /Users/mlinnane/repos/BCD-Interactive-City-Scale-Models/Dublin/Fabrication/Sources/Grids_Extents/Print Tiles Dublin Boundary 7x4km 1-2000 1km Tile/Print Tiles Dublin Boundary 7x4km 1-2000 1km Tile.shp   # Source Esri Shapefile(s)
- DestDataset_OGCKML = $(FME_MF_DIR)Issue Placemarks/Tiled/test   # Destination Google KML File
- SourceDataset_OGCKML = $(FME_MF_DIR)Issue Placemarks/Raw/D2-D3-D4_1st Pass.kmz   # Source Google KML File or URL
- DestDataset_CSV2 = $(FME_MF_DIR)Issue Placemarks/Lists/test   # Destination CSV (Comma Separated Value) Folder
- SourceDataset_OGCKML_19 = $(FME_MF_DIR)Issue Placemarks/Raw/B1 B2 B3Liam_places.kmz   # Source Google KML File or URL
- SourceDataset_OGCKML_15 = $(FME_MF_DIR)Issue Placemarks/Raw/C2_Notes Bashir.kmz   # Source Google KML File or URL
- SourceDataset_OGCKML_23 = $(FME_MF_DIR)Issue Placemarks/Raw/C3_C4_D1 Olly_.kmz   # Source Google KML File or URL
- SourceDataset_OGCKML_17 = $(FME_MF_DIR)Issue Placemarks/Raw/E1_E2_E3.kmz   # Source Google KML File or URL
- SourceDataset_OGCKML_21 = $(FME_MF_DIR)Issue Placemarks/Raw/E4_byw.kmz   # Source Google KML File or URL
- SourceDataset_OGCKML_14 = $(FME_MF_DIR)Issue Placemarks/Raw/f1_byw.kmz   # Source Google KML File or URL
- SourceDataset_OGCKML_16 = $(FME_MF_DIR)Issue Placemarks/Raw/f2_byw.kmz   # Source Google KML File or URL
- SourceDataset_OGCKML_18 = $(FME_MF_DIR)Issue Placemarks/Raw/F3 F4 G1 tiles RK.kmz   # Source Google KML File or URL
- SourceDataset_OGCKML_20 = $(FME_MF_DIR)Issue Placemarks/Raw/G2 G3 G4 jeneentiles.kmz   # Source Google KML File or URL
- SourceDataset_OGCKML_12 = $(FME_MF_DIR)Issue Placemarks/Raw/A4_byw.kmz   # Source Google KML File or URL
- SourceDataset_OGCKML_22 = $(FME_MF_DIR)Issue Placemarks/Raw/My Places.kml   # Source Google KML File or URL

Readers:
- ESRISHAPE_1: ESRISHAPE from $(SourceDataset_ESRISHAPE)
- OGCKML_1: OGCKML from $(SourceDataset_OGCKML)
- OGCKML_2: OGCKML from $(SourceDataset_OGCKML_12)
- OGCKML_3: OGCKML from $(SourceDataset_OGCKML_19)
- OGCKML_4: OGCKML from $(SourceDataset_OGCKML_15)
- OGCKML_5: OGCKML from $(SourceDataset_OGCKML_23)
- OGCKML_6: OGCKML from $(SourceDataset_OGCKML_17)
- OGCKML_7: OGCKML from $(SourceDataset_OGCKML_21)
- OGCKML_8: OGCKML from $(SourceDataset_OGCKML_14)
- OGCKML_9: OGCKML from $(SourceDataset_OGCKML_16)
- OGCKML_10: OGCKML from $(SourceDataset_OGCKML_18)
- OGCKML_11: OGCKML from $(SourceDataset_OGCKML_20)
- OGCKML_13: OGCKML from $(SourceDataset_OGCKML_22)

Writers:
- OGCKML_12: OGCKML to $(DestDataset_OGCKML)
- CSV2_1: CSV2 to $(DestDataset_CSV2)

Print Tiles Dublin Boundary 7x4km 1-2000 1km Tile (reader ESRISHAPE_1)
    attributes: left double, top double, right double, bottom double, id long
    -> AttributeManager_2
AttributeManager_2
    ATTR_TABLE = SET_TO id = FME_CONDITIONAL:DEFAULT_VALUE'_FME_NO_OP_'BOOL_OP;OR;COMPOSITE_TEST;1;TEST @Value(id) = 1'A1'BOOL_OP;OR;COMPOSITE_TEST;1;TEST @Value(id) = 2'A2'BOOL_OP;OR;COMPOSITE_TEST;1;TEST @Value(id) = 3'A3'BOOL_OP;OR;COMPOSITE_TEST;1;TEST @Value(id) = 4'A4'BOOL_OP;OR;COMPOSITE_TEST;1;TEST @Value(id) = 5'B1'BOOL_OP;OR;COMPOSITE_TEST;1;TEST @Value(id) = 6'B2'BOOL_OP;OR;COMPOSITE_TEST;1;TEST @Value(id) = 7'B3'BOOL_OP;OR;COMPOSITE_TEST;1;TEST @Value(id) = 8'B4'BOOL_OP;OR;COMPOSITE_TEST;1;TEST @Value(id) = 9'C1'BOOL_OP;OR;COMPOSITE_TEST;1;TEST @Value(id) = 10'C2'BOOL_OP;OR;COMPOSITE_TEST;1;TEST @Value(id) = 11'C3'BOOL_OP;OR;COMPOSITE_TEST;1;TEST @Value(id) = 12'C4'BOOL_OP;OR;COMPOSITE_TEST;1;TEST @Value(id) = 13'D1'BOOL_OP;OR;COMPOSITE_TEST;1;TEST @Value(id) = 14'D2'BOOL_OP;OR;COMPOSITE_TEST;1;TEST @Value(id) = 15'D3'BOOL_OP;OR;COMPOSITE_TEST;1;TEST @Value(id) = 16'D4'BOOL_OP;OR;COMPOSITE_TEST;1;TEST @Value(id) = 17'E1'BOOL_OP;OR;COMPOSITE_TEST;1;TEST @Value(id) = 18'E2'BOOL_OP;OR;COMPOSITE_TEST;1;TEST @Value(id) = 19'E3'BOOL_OP;OR;COMPOSITE_TEST;1;TEST @Value(id) = 20'E4'BOOL_OP;OR;COMPOSITE_TEST;1;TEST @Value(id) = 21'F1'BOOL_OP;OR;COMPOSITE_TEST;1;TEST @Value(id) = 22'F2'BOOL_OP;OR;COMPOSITE_TEST;1;TEST @Value(id) = 23'F3'BOOL_OP;OR;COMPOSITE_TEST;1;TEST @Value(id) = 24'F4'BOOL_OP;OR;COMPOSITE_TEST;1;TEST @Value(id) = 25'G1'BOOL_OP;OR;COMPOSITE_TEST;1;TEST @Value(id) = 26'G2'BOOL_OP;OR;COMPOSITE_TEST;1;TEST @Value(id) = 27'G3'BOOL_OP;OR;COMPOSITE_TEST;1;TEST @Value(id) = 28'G4'FME_NUM_CONDITIONS29___
    -> Clipper [CLIPPER]
Placemark (reader OGCKML_2)
    -> Reprojector
Placemark (reader OGCKML_3)
    -> Reprojector
Placemark (reader OGCKML_4)
    -> Reprojector
Placemark (reader OGCKML_5)
    -> Reprojector
Placemark (reader OGCKML_1)
    -> Reprojector
Placemark (reader OGCKML_6)
    -> Reprojector
Placemark (reader OGCKML_7)
    -> Reprojector
Placemark (reader OGCKML_8)
    -> Reprojector
Placemark (reader OGCKML_9)
    -> Reprojector
Placemark (reader OGCKML_10)
    -> Reprojector
Placemark (reader OGCKML_11)
    -> Reprojector
Placemark (reader OGCKML_13)
    -> Reprojector
Reprojector
    DEST = EPSG:2157
    INTERPOLATION_TYPE_NAME = Nearest Neighbor
    RASTER_CELL_SIZE = Preserve Cells
    RASTER_TOLERANCE = 0.0
    SOURCE = Read from feature
    REPROJECTED -> Clipper [CLIPPEE]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Counter
Counter
    CNT_ATTR = _count
    DOMAIN = @Value(id)
    SCOPE = Local
    START = 1
    -> AttributeManager
AttributeManager
    ATTR_TABLE = SET_TO kml_id = @Value(id).@Value(_count)
    -> KMLPropertySetter
KMLPropertySetter
    ADD_ATTR_TABLE = Yes
    ATTR_TABLE_TITLE = Attributes
    CONTENT_TYPE = Text
    EXTRUDE = No
    GEOM_TYPE = Vector
    NAME = @Value(kml_id)
    SUMMARY = <none>
    TESSELATE = Yes
    VISIBILITY = Yes
    -> Placemarks (writer OGCKML_12)
    -> File1 (writer CSV2_1)
Placemarks (writer OGCKML_12)
File1 (writer CSV2_1)
    attributes: left string, top string, right string, bottom string, id string, kml_id string, _clipped string, _count string
