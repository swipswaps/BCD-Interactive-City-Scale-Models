FME workspace Luas_JSON_Flattening.fmw

Parameters:
- SourceDataset_TEXTLINE = ""C:\Users\odawkins\Downloads\luas-data-sample\luas-data-sample\2019-10-16-18\luas-1571245200008.json" "C:\Users\odawkins\Downloads\luas-data-sample\luas-data-sample\2019-10-16-18\luas-1571245260007.json" "C:\Users\odawkins\Downloads\luas-data-sample\luas-data-sample\2019-10-16-18\luas-1571245320009.json" "C:\Users\odawkins\Downloads\luas-data-sample\luas-data-sample\2019-10-16-18\luas-1571245380009.json" "C:\Users\odawkins\Downloads\luas-data-sample\luas-data-sample\2019-10-16-18\luas-1571245440009.json" "C:\Users\odawkins\Downloads\luas-data-sample\luas-data-sample\2019-10-16-18\luas-1571245500006.json" "C:\Users\odawkins\Downloads\luas-data-sample\luas-data-sample\2019-10-16-18\luas-1571245560011.json" "C:\Users\odawkins\Downloads\luas-data-sample\luas-data-sample\2019-10-16-18\luas-1571245620002.json" "C:\Users\odawkins\Downloads\luas-data-sample\luas-data-sample\2019-10-16-18\luas-1571245680012.json" "C:\Users\odawkins\Downloads\luas-data-sample\luas-data-sample\2019-10-16-18\luas-1571245740006.json" "C:\Users\odawkins\Downloads\luas-data-sample\luas-data-sample\2019-10-16-18\luas-1571245800007.json" "C:\Users\odawkins\Downloads\luas-data-sample\luas-data-sample\2019-10-16-18\luas-1571245860006.json" "C:\Users\odawkins\Downloads\luas-data-sample\luas-data-sample\2019-10-16-18\luas-1571245920007.json" "C:\Users\odawkins\Downloads\luas-data-sample\luas-data-sample\2019-10-16-18\luas-1571245980002.json" "C:\Users\odawkins\Downloads\luas-data-sample\luas-data-sample\2019-10-16-18\luas-1571246040007.json" "C:\Users\odawkins\Downloads\luas-data-sample\luas-data-sample\2019-10-16-18\luas-1571246100009.json" "C:\Users\odawkins\Downloads\luas-data-sample\luas-data-sample\2019-10-16-18\luas-1571246160009.json" "C:\Users\odawkins\Downloads\luas-data-sample\luas-data-sample\2019-10-16-18\luas-1571246220011.json" "C:\Users\odawkins\Downloads\luas-data-sample\luas-data-sample\2019-10-16-18\luas-1571246280007.json" "C:\Users\odawkins\Downloads\luas-data-sample\luas-data-sample\2019-10-16-18\luas-1571246340008.json" "C:\Users\odawkins\Downloads\luas-data-sample\luas-data-sample\2019-10-16-18\luas-1571246400008.json" "C:\Users\odawkins\Downloads\luas-data-sample\luas-data-sample\2019-10-16-18\luas-1571246460009.json" "C:\Users\odawkins\Downloads\luas-data-sample\luas-data-sample\2019-10-16-18\luas-1571246520008.json" "C:\Users\odawkins\Downloads\luas-data-sample\luas-data-sample\2019-10-16-18\luas-1571246580009.json" "C:\Users\odawkins\Downloads\luas-data-sample\luas-data-sample\2019-10-16-18\luas-1571246640010.json" "C:\Users\odawkins\Downloads\luas-data-sample\luas-data-sample\2019-10-16-18\luas-1571246700009.json" "C:\Users\odawkins\Downloads\luas-data-sample\luas-data-sample\2019-10-16-18\luas-1571246760006.json" "C:\Users\odawkins\Downloads\luas-data-sample\luas-data-sample\2019-10-16-18\luas-1571246820002.json" "C:\Users\odawkins\Downloads\luas-data-sample\luas-data-sample\2019-10-16-18\luas-1571246880010.json" "C:\Users\odawkins\Downloads\luas-data-sample\luas-data-sample\2019-10-16-18\luas-1571246940007.json" "C:\Users\odawkins\Downloads\luas-data-sample\luas-data-sample\2019-10-16-18\luas-1571247000002.json" "C:\Users\odawkins\Downloads\luas-data-sample\luas-data-sample\2019-10-16-18\luas-1571247060002.json" "C:\Users\odawkins\Downloads\luas-data-sample\luas-data-sample\2019-10-16-18\luas-1571247120002.json" "C:\Users\odawkins\Downloads\luas-data-sample\luas-data-sample\2019-10-16-18\luas-1571247180010.json" "C:\Users\odawkins\Downloads\luas-data-sample\luas-data-sample\2019-10-16-18\luas-1571247240010.json" "C:\Users\odawkins\Downloads\luas-data-sample\luas-data-sample\2019-10-16-18\luas-1571247300002.json" "C:\Users\odawkins\Downloads\luas-data-sample\luas-data-sample\2019-10-16-18\luas-1571247360010.json" "C:\Users\odawkins\Downloads\luas-data-sample\luas-data-sample\2019-10-16-18\luas-1571247420010.json" "C:\Users\odawkins\Downloads\luas-data-sample\luas-data-sample\2019-10-16-18\luas-1571247480010.json" "C:\Users\odawkins\Downloads\luas-data-sample\luas-data-sample\2019-10-16-18\luas-1571247540004.json" "C:\Users\odawkins\Downloads\luas-data-sample\luas-data-sample\2019-10-16-18\luas-1571247600007.json" "C:\Users\odawkins\Downloads\luas-data-sample\luas-data-sample\2019-10-16-18\luas-1571247660008.json" "C:\Users\odawkins\Downloads\luas-data-sample\luas-data-sample\2019-10-16-18\luas-1571247720008.json" "C:\Users\odawkins\Downloads\luas-data-sample\luas-data-sample\2019-10-16-18\luas-1571247780009.json" "C:\Users\odawkins\Downloads\luas-data-sample\luas-data-sample\2019-10-16-18\luas-1571247840003.json" "C:\Users\odawkins\Downloads\luas-data-sample\luas-data-sample\2019-10-16-18\luas-1571247900011.json" "C:\Users\odawkins\Downloads\luas-data-sample\luas-data-sample\2019-10-16-18\luas-1571247960010.json" "C:\Users\odawkins\Downloads\luas-data-sample\luas-data-sample\2019-10-16-18\luas-1571248020005.json" "C:\Users\odawkins\Downloads\luas-data-sample\luas-data-sample\2019-10-16-18\luas-1571248080004.json" "C:\Users\odawkins\Downloads\luas-data-sample\luas-data-sample\2019-10-16-18\luas-1571248140010.json" "C:\Users\odawkins\Downloads\luas-data-sample\luas-data-sample\2019-10-16-18\luas-1571248200010.json" "C:\Users\odawkins\Downloads\luas-data-sample\luas-data-sample\2019-10-16-18\luas-1571248260004.json" "C:\Users\odawkins\Downloads\luas-data-sample\luas-data-sample\2019-10-16-18\luas-1571248320012.json" "C:\Users\odawkins\Downloads\luas-data-sample\luas-data-sample\2019-10-16-18\luas-1571248380008.json" "C:\Users\odawkins\Downloads\luas-data-sample\luas-data-sample\2019-10-16-18\luas-1571248440009.json" "C:\Users\odawkins\Downloads\luas-data-sample\luas-data-sample\2019-10-16-18\luas-1571248500003.json" "C:\Users\odawkins\Downloads\luas-data-sample\luas-data-sample\2019-10-16-18\luas-1571248560001.json" "C:\Users\odawkins\Downloads\luas-data-sample\luas-data-sample\2019-10-16-18\luas-1571248620010.json" "C:\Users\odawkins\Downloads\luas-data-sample\luas-data-sample\2019-10-16-18\luas-1571248680001.json" "C:\Users\odawkins\Downloads\luas-data-sample\luas-data-sample\2019-10-16-18\luas-1571248740005.json""   # Source Text File(s)
- DestDataset_CSV2 = D:\Processed_Data\luas-data   # Destination CSV (Comma Separated Value) Folder
- SourceDataset_JSON = ""C:\Users\odawkins\Downloads\luas-data-sample\luas-data-sample\2019-10-16-18\luas-1571245200008.json" "C:\Users\odawkins\Downloads\luas-data-sample\luas-data-sample\2019-10-16-18\luas-1571245260007.json" "C:\Users\odawkins\Downloads\luas-data-sample\luas-data-sample\2019-10-16-18\luas-1571245320009.json" "C:\Users\odawkins\Downloads\luas-data-sample\luas-data-sample\2019-10-16-18\luas-1571245380009.json" "C:\Users\odawkins\Downloads\luas-data-sample\luas-data-sample\2019-10-16-18\luas-1571245440009.json" "C:\Users\odawkins\Downloads\luas-data-sample\luas-data-sample\2019-10-16-18\luas-1571245500006.json" "C:\Users\odawkins\Downloads\luas-data-sample\luas-data-sample\2019-10-16-18\luas-1571245560011.json" "C:\Users\odawkins\Downloads\luas-data-sample\luas-data-sample\2019-10-16-18\luas-1571245620002.json" "C:\Users\odawkins\Downloads\luas-data-sample\luas-data-sample\2019-10-16-18\luas-1571245680012.json" "C:\Users\odawkins\Downloads\luas-data-sample\luas-data-sample\2019-10-16-18\luas-1571245740006.json" "C:\Users\odawkins\Downloads\luas-data-sample\luas-data-sample\2019-10-16-18\luas-1571245800007.json" "C:\Users\odawkins\Downloads\luas-data-sample\luas-data-sample\2019-10-16-18\luas-1571245860006.json" "C:\Users\odawkins\Downloads\luas-data-sample\luas-data-sample\2019-10-16-18\luas-1571245920007.json" "C:\Users\odawkins\Downloads\luas-data-sample\luas-data-sample\2019-10-16-18\luas-1571245980002.json" "C:\Users\odawkins\Downloads\luas-data-sample\luas-data-sample\2019-10-16-18\luas-1571246040007.json" "C:\Users\odawkins\Downloads\luas-data-sample\luas-data-sample\2019-10-16-18\luas-1571246100009.json" "C:\Users\odawkins\Downloads\luas-data-sample\luas-data-sample\2019-10-16-18\luas-1571246160009.json" "C:\Users\odawkins\Downloads\luas-data-sample\luas-data-sample\2019-10-16-18\luas-1571246220011.json" "C:\Users\odawkins\Downloads\luas-data-sample\luas-data-sample\2019-10-16-18\luas-1571246280007.json" "C:\Users\odawkins\Downloads\luas-data-sample\luas-data-sample\2019-10-16-18\luas-1571246340008.json" "C:\Users\odawkins\Downloads\luas-data-sample\luas-data-sample\2019-10-16-18\luas-1571246400008.json" "C:\Users\odawkins\Downloads\luas-data-sample\luas-data-sample\2019-10-16-18\luas-1571246460009.json" "C:\Users\odawkins\Downloads\luas-data-sample\luas-data-sample\2019-10-16-18\luas-1571246520008.json" "C:\Users\odawkins\Downloads\luas-data-sample\luas-data-sample\2019-10-16-18\luas-1571246580009.json" "C:\Users\odawkins\Downloads\luas-data-sample\luas-data-sample\2019-10-16-18\luas-1571246640010.json" "C:\Users\odawkins\Downloads\luas-data-sample\luas-data-sample\2019-10-16-18\luas-1571246700009.json" "C:\Users\odawkins\Downloads\luas-data-sample\luas-data-sample\2019-10-16-18\luas-1571246760006.json" "C:\Users\odawkins\Downloads\luas-data-sample\luas-data-sample\2019-10-16-18\luas-1571246820002.json" "C:\Users\odawkins\Downloads\luas-data-sample\luas-data-sample\2019-10-16-18\luas-1571246880010.json" "C:\Users\odawkins\Downloads\luas-data-sample\luas-data-sample\2019-10-16-18\luas-1571246940007.json" "C:\Users\odawkins\Downloads\luas-data-sample\luas-data-sample\2019-10-16-18\luas-1571247000002.json" "C:\Users\odawkins\Downloads\luas-data-sample\luas-data-sample\2019-10-16-18\luas-1571247060002.json" "C:\Users\odawkins\Downloads\luas-data-sample\luas-data-sample\2019-10-16-18\luas-1571247120002.json" "C:\Users\odawkins\Downloads\luas-data-sample\luas-data-sample\2019-10-16-18\luas-1571247180010.json" "C:\Users\odawkins\Downloads\luas-data-sample\luas-data-sample\2019-10-16-18\luas-1571247240010.json" "C:\Users\odawkins\Downloads\luas-data-sample\luas-data-sample\2019-10-16-18\luas-1571247300002.json" "C:\Users\odawkins\Downloads\luas-data-sample\luas-data-sample\2019-10-16-18\luas-1571247360010.json" "C:\Users\odawkins\Downloads\luas-data-sample\luas-data-sample\2019-10-16-18\luas-1571247420010.json" "C:\Users\odawkins\Downloads\luas-data-sample\luas-data-sample\2019-10-16-18\luas-1571247480010.json" "C:\Users\odawkins\Downloads\luas-data-sample\luas-data-sample\2019-10-16-18\luas-1571247540004.json" "C:\Users\odawkins\Downloads\luas-data-sample\luas-data-sample\2019-10-16-18\luas-1571247600007.json" "C:\Users\odawkins\Downloads\luas-data-sample\luas-data-sample\2019-10-16-18\luas-1571247660008.json" "C:\Users\odawkins\Downloads\luas-data-sample\luas-data-sample\2019-10-16-18\luas-1571247720008.json" "C:\Users\odawkins\Downloads\luas-data-sample\luas-data-sample\2019-10-16-18\luas-1571247780009.json" "C:\Users\odawkins\Downloads\luas-data-sample\luas-data-sample\2019-10-16-18\luas-1571247840003.json" "C:\Users\odawkins\Downloads\luas-data-sample\luas-data-sample\2019-10-16-18\luas-1571247900011.json" "C:\Users\odawkins\Downloads\luas-data-sample\luas-data-sample\2019-10-16-18\luas-1571247960010.json" "C:\Users\odawkins\Downloads\luas-data-sample\luas-data-sample\2019-10-16-18\luas-1571248020005.json" "C:\Users\odawkins\Downloads\luas-data-sample\luas-data-sample\2019-10-16-18\luas-1571248080004.json" "C:\Users\odawkins\Downloads\luas-data-sample\luas-data-sample\2019-10-16-18\luas-1571248140010.json" "C:\Users\odawkins\Downloads\luas-data-sample\luas-data-sample\2019-10-16-18\luas-1571248200010.json" "C:\Users\odawkins\Downloads\luas-data-sample\luas-data-sample\2019-10-16-18\luas-1571248260004.json" "C:\Users\odawkins\Downloads\luas-data-sample\luas-data-sample\2019-10-16-18\luas-1571248320012.json" "C:\Users\odawkins\Downloads\luas-data-sample\luas-data-sample\2019-10-16-18\luas-1571248380008.json" "C:\Users\odawkins\Downloads\luas-data-sample\luas-data-sample\2019-10-16-18\luas-1571248440009.json" "C:\Users\odawkins\Downloads\luas-data-sample\luas-data-sample\2019-10-16-18\luas-1571248500003.json" "C:\Users\odawkins\Downloads\luas-data-sample\luas-data-sample\2019-10-16-18\luas-1571248560001.json" "C:\Users\odawkins\Downloads\luas-data-sample\luas-data-sample\2019-10-16-18\luas-1571248620010.json" "C:\Users\odawkins\Downloads\luas-data-sample\luas-data-sample\2019-10-16-18\luas-1571248680001.json" "C:\Users\odawkins\Downloads\luas-data-sample\luas-data-sample\2019-10-16-18\luas-1571248740005.json""   # Source JSON (JavaScript Object Notation) File or URL
- DestDataset_CSV2_5 = C:\Users\odawkins\Desktop   # Destination CSV (Comma Separated Value) Folder
- DestDataset_CSV2_4 = D:\Processed_Data\luas-data   # Destination CSV (Comma Separated Value) Folder

Readers:
- TEXTLINE_1: TEXTLINE from $(SourceDataset_TEXTLINE)
- JSON_1: JSON from $(SourceDataset_JSON)

Writers:
- CSV2_1: CSV2 to $(DestDataset_CSV2)
- CSV2_2: CSV2 to $(DestDataset_CSV2_5)
- CSV2_3: CSV2 to $(DestDataset_CSV2_4)

Bookmark: BCD LUAS API Output File Processing
Note: Data Source: / BCD LUAS API / NOTE: This flow is used for flattening the API output. Flattended data is currently output to CSV, with a separate file for every separate input file. Empty fields are included in the output.
JSONFeature (reader JSON_1)
    attributes: stopID string, stopQueryTime int, count int, results{}.Direction string, results{}.Destination string, results{}.Time string, results{}.AVLS string, results{}.Tram string, results{}.Action string, results{}.Msg Sent string, results{}.Msg Received string, results{}.Msg Processed string, results{}.XML ID string, results{}.Total Lag string, results{}.Create Lag string, results{}.Process Lag string
    -> ListExploder
Note: List Exploder Paramenters: / 1. List Attribute = 'results{}' / NOTE: Stations with empty results are fed back in to the flow.
ListExploder
    ATTR_ACCUM_MODE = Merge List Attributes
    ATTR_CONFLICT_RES = Use List Attribute Values
    INDEX_ATTR = _element_index
    LIST_ATTR = results{}
    ELEMENTS -> AttributeManager_2
    <REJECTED> -> AttributeManager_2
AttributeManager_2
    ATTR_TABLE:
      REMOVE _element_index
      REMOVE fme_rejection_code
    -> JSONFeature (writer CSV2_3)
    -> Inspector_2
JSONFeature (writer CSV2_3)
    attributes: stopID string, stopQueryTime string, count string, Direction string, Destination string, Time string, AVLS string, Tram string, Action string, Msg Sent string, Msg Received string, Msg Processed string, XML ID string, Total Lag string, Create Lag string, Process Lag string
Note: CSV Writer Paramenters: / 1. SELECT FILE OUTPUT FOLDER / 2. Output filename = 'fme_basename' (i.e. matches input filename)
Inspector_2

Bookmark: For Debugging Purposes ONLY - JSON is loaded as Text and iteratively fragmented
text_line (reader TEXTLINE_1)
    attributes: text_line_data buffer
    -> JSONFragmenter
JSONFragmenter
    EXPLODE_FORMAT = JSON
    EXTRACT_ATTR = No
    JSON_ATTR = text_line_data
    JSON_QUERY = json[*]
    READ_FROM_FILE = NO
    REJECT_EMPTY_LISTS = YES
    FRAGMENTS -> JSONExtractor
    <REJECTED> -> Junction
JSONExtractor
    EXTRACT_QUERY_TABLE = stopID json["stopID"] stopQueryTime json["stopQueryTime"] count json["count"] results json["results"]
    JSON_DOCUMENT = @Value(text_line_data)
    READ_FROM_FILE = NO
    EVALUATED -> JSONFragmenter_3
    <REJECTED> -> Junction
JSONFragmenter_3
    EXPLODE_FORMAT = JSON
    EXTRACT_ATTR = No
    JSON_ATTR = results
    JSON_QUERY = json[*]
    READ_FROM_FILE = NO
    REJECT_EMPTY_LISTS = YES
    FRAGMENTS -> JSONExtractor_2
    <REJECTED> -> Junction
    <REJECTED> -> AttributeManager
JSONExtractor_2
    EXTRACT_QUERY_TABLE = Direction json["Direction"] Destination json["Destination"] Time json["Time"] AVLS json["AVLS"] Tram json["Tram"] Action json["Action"] "Msg Sent" json["Msg Sent"] "Msg Received" json["Msg Received"] "Msg Processed" json["Msg Processed"] "XML ID" json["XML ID"] "Total Lag" json["Total Lag"] "Create Lag" json["Create Lag"] "Process Lag" json["Process Lag"]
    JSON_DOCUMENT = @Value(results)
    READ_FROM_FILE = NO
    EVALUATED -> AttributeManager
    <REJECTED> -> Junction
AttributeManager
    ATTR_TABLE:
      REMOVE text_line_data
      REMOVE json_type
      REMOVE json_index
      REMOVE results
      REMOVE fme_rejection_code
    -> text_line (writer CSV2_1)
text_line (writer CSV2_1)
    attributes: stopID string, stopQueryTime string, count string, Direction string, Destination string, Time string, AVLS string, Tram string, Action string, Msg Sent string, Msg Received string, Msg Processed string, XML ID string, Total Lag string, Create Lag string, Process Lag string
Junction
    -> Inspector
Inspector
