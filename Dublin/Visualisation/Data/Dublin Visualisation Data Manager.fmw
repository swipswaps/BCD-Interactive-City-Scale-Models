FME workspace Dublin Visualisation Data Manager.fmw
Title: OSiDataTo3D

Parameters:
- SourceDataset_FILEGDB_3 = $(FME_MF_DIR)LiDAR_Footprints/DublinBuildingGrangeGormantoDocks.gdb   # File Geodatabase
- SourceDataset_LAS = $(FME_MF_DIR)LiDAR_Footprints/docklands_lidar_2009_dsm.las   # Source ASPRS LAS File(s)
- DestDataset_STL_3 = /Users/mlinnane/OneDrive - Maynooth University/BCD/Architectural Model/Data/Output   # Destination STL Folder
- SourceDataset_ESRISHAPE_9 = /Users/mlinnane/Documents/GitHub local copy/BCD-Architectural-Models/Grids/0.4/Tiles v0.4.shp   # Source Esri Shapefile(s)
- ELEVATION = -8   # Planar Surface Elevation
- SourceDataset_ESRISHAPE = /Users/mlinnane/Documents/github/BCD-Interactive-Architectural-City-Models/Grids/Non-national grid/240m2/Tiles 240m2.shp   # Source Esri Shapefile(s)
- SourceDataset_ESRISHAPE_13 = /Users/mlinnane/Documents/github/BCD-Interactive-Architectural-City-Models/Grids/Non-national grid/120m2/Tiles 120m2.shp   # Source Esri Shapefile(s)
- SourceDataset_ESRISHAPE_11 = /Users/mlinnane/Documents/github/BCD-Interactive-Architectural-City-Models/Grids/Grid 500m2/Grid 500m2.shp   # Source Esri Shapefile(s)
- SourceDataset_ESRISHAPE_8 = /Users/mlinnane/Documents/github/BCD-Interactive-Architectural-City-Models/Grids/Grid 400m2/Grid 400m2.shp   # Source Esri Shapefile(s)
- SourceDataset_ESRISHAPE_12 = /Users/mlinnane/Documents/github/BCD-Interactive-Architectural-City-Models/Grids/Grid 1km2/Grid 1km2.shp   # Source Esri Shapefile(s)
- DestDataset_TIFF = /Users/mlinnane/OneDrive - Maynooth University/BCD/Architectural Model/Data/Output/Images   # Destination TIFF (Tagged Image File Format) Folder
- DestDataset_IEPS = /Users/mlinnane/Desktop/test.eps   # Destination Adobe Illustrator EPS File
- DestDataset_ESRISHAPE = /Users/mlinnane/OneDrive - Maynooth University/BCD/Architectural Model/Viz   # Destination Esri Shapefile Folder
- DestDataset_ESRISHAPE_2 = /Users/mlinnane/OneDrive - Maynooth University/BCD/Architectural Model/Viz/Building Footprints   # Destination Esri Shapefile Folder

Readers:
- FILEGDB_1: FILEGDB from $(SourceDataset_FILEGDB_3)
- LAS_1: LAS from $(SourceDataset_LAS) in EPSG:2157
- ESRISHAPE_1: ESRISHAPE from $(SourceDataset_ESRISHAPE_9)
- ESRISHAPE_2: ESRISHAPE from $(SourceDataset_ESRISHAPE)
- ESRISHAPE_3: ESRISHAPE from $(SourceDataset_ESRISHAPE_13)
- ESRISHAPE_4: ESRISHAPE from $(SourceDataset_ESRISHAPE_11)
- ESRISHAPE_5: ESRISHAPE from $(SourceDataset_ESRISHAPE_8)
- ESRISHAPE_6: ESRISHAPE from $(SourceDataset_ESRISHAPE_12)

Writers:
- STL_1: STL to $(DestDataset_STL_3)
- TIFF_1: TIFF to $(DestDataset_TIFF)
- IEPS_1: IEPS to $(DestDataset_IEPS)
- ESRISHAPE_7: ESRISHAPE to $(DestDataset_ESRISHAPE)
- ESRISHAPE_8: ESRISHAPE to $(DestDataset_ESRISHAPE_2) in EPSG:2157

Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> FeatureColorSetter_2
Note: Filter for Point Cloud features
PointCloudFilter
    FILTER_TABLE = EXPRESSION_LIST @Component(classification)==1 ; @Component(classification)==2 FILTER_ATTRIBUTE __pc_internal_filter_attribute__ FILTER_ATTRIBUTE_VALUES_LIST Feature ; Ground
    OUTPUT_UNFILTERED_POINTS = Yes
    Feature -> Clipper [CLIPPEE]
    Ground -> SurfaceModeller [POINTS/LINES]
Note: Extract tile by id
406: AttributeFilter
    ATTR_NAME = id
    ATTR_VALUES = 148,149,161,162,194,195,207,208,213,214,215,229,230,231,245,246,247,406,1582,2575,3390,3391,3392,3520,3521,3522,3650,3651,3652,<Empty>,<Missing>,<Null>,<Unfiltered>
    3390 -> Junction_8
    3391 -> Junction_8
    3392 -> Junction_8
    3392 -> Inspector_4
    3520 -> Junction_8
    3521 -> Junction_8
    3522 -> Junction_8
    3650 -> Junction_8
    3651 -> Junction_8
    3652 -> Junction_8
Junction_8
    -> Clipper_4 [CLIPPER]
Inspector_4
Junction_2
    -> Junction_4
    -> SurfaceModeller [DRAPE_FEATURES]
    -> Clipper_4 [CLIPPER]
Clipper_4
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> FeatureColorSetter_2
    INSIDE -> Inspector_5
Inspector_5
FeatureColorSetter_2
    COLOR = 0,0,0
    FILL_COLOR = 0,0,0
    MODE = Fixed
    COLORED -> AttributeCreator_4
AttributeCreator_4
    ATTR_TABLE = SET_TO Order = 1
    -> Sorter
Sorter
    SORT_PARM = Order NUMERIC DESCENDING
    SORTED -> ImageRasterizer_2
ImageRasterizer_2
    ALPHA = 0
    ANTI_ALIASING = Yes
    BACKGROUND_ALPHA = 1
    BACKGROUND_COLOR = 0.843137,1,0.0745098
    FILL_WITH_NODATA = No
    INTERPRETATION_TYPE = RGBA32
    ROWCOL_OR_CELLSIZE = CellSize
    SPECIFY_GROUND_EXTENTS = Use input data ground extents
    X_CELL_SIZE = 0.2
    Y_CELL_SIZE = 0.2
    RASTER -> Inspector_3
    RASTER -> BuildingFootprints (writer TIFF_1)
BuildingFootprints (writer TIFF_1)
    attributes: GUID char(114), FORM_VALUE char(120), FUNC_VALUE char(240), POLY_GEOM_CAPTURE_DATE datetime, POLY_GEOM_CHANGE_DATE datetime, WAY_SEG_VALUE char(114), STATUS_VALUE char(120), Z_ORDER_VALUE float, OBJECTID integer
Inspector_3
Note: Build surface model / Drape clipping boundary / Output triangles / https://knowledge.safe.com/articles/1310/how-to-clip-tin-surfaces.html
SurfaceModeller
    CONTOUR_DIMENSION = 3
    CONTOUR_INTERVAL = 100.0
    DRAPE_TYPE = VERTEX
    ELEV_ATTR = _elevation
    IGNORE_INPUT_ON_INTERVAL = Perturb Input Points On Contour Interval
    INTERPOLATION_TYPE = AUTO
    NODATA_VALUE = -32767.0
    TOLERANCE = 0.165
    X_SPACING = 100.0
    Y_SPACING = 100.0
    DRAPED_FEATURES -> Clipper_3 [CLIPPER]
    TRIANGLES -> Clipper_3 [CLIPPEE]
Note: Clip triangles by boundary
Clipper_3
    ATTR_PREFIX = clipper_
    BOUNDARY_CASES = Treat as Inside
    CLIP_TYPE = Multiple Clippers
    CREATE_AGGREGATES = Yes
    MERGE_ATTRS = No
    PRESERVE_CLIPPEE_EXTENTS = No
    INSIDE -> FaceReplacer_2
    CLIPPED_INSIDE -> FaceReplacer_2
Note: Replace polygons with faces
FaceReplacer_2
    CHECK_PLANARITY = No
    PLANARITY_TOLERANCE = 0.0
    -> Aggregator_2
Note: Aggregate faces into multi-surface
Aggregator_2
    ACCUM_ATTRS_NAME = Yes
    CONTAIN_INDIVID_GEOMS = No
    ORDERED = No
    SEP = ,
    AGGREGATE -> Deaggregator
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> AggregateFilter
AggregateFilter
    AGGREGATE -> AttributeCreator_3
    NOT_AGGREGATE -> GeometryFilter
GeometryFilter
    BREAK_AGG = No
    GEOM_PORT_NAMES = Surface
    SURFACE -> BoundsExtractor
    <UNFILTERED> -> AttributeCreator_3
BoundsExtractor
    ZMAX = __ssc.zmax
    ZMIN = __ssc.zmin
    -> AttributeCreator
AttributeCreator
    ATTR_TABLE:
      SET_TO __ssc.elevation = $(ELEVATION)
      SET_TO __ssc.flag = FME_CONDITIONAL:DEFAULT_VALUE'0'BOOL_OP;OR;COMPOSITE_TEST;<Unused>;TEST $(ELEVATION) < @Value(__ssc.zmin)'-1'BOOL_OP;OR;COMPOSITE_TEST;<Unused>;TEST @Value(__ssc.zmax) < $(ELEVATION)'1'FME_NUM_CONDITIONS3___
    -> Tester
Tester
    BOOL_OP = OR
    COMPOSITE_TEST = 1
    TEST_CLAUSE = TEST @Value(__ssc.flag) != 0
    TEST_MODE = TEST
    PASSED -> Counter
    FAILED -> AttributeCreator_2
Counter
    CNT_ATTR = __ssc.id
    DOMAIN = counter_id
    SCOPE = Local
    START = 0
    -> PythonCaller
    -> Tester_2
Tester_2
    BOOL_OP = OR
    TEST_CLAUSE = TEST @Value(__ssc.flag) < 0
    TEST_MODE = Automatic
    PASSED -> Tester_3_PASSED
    FAILED -> Orientor
Note: Top
Tester_3_PASSED: Junction
    -> Top_2
Orientor
    FLIP_APPEARANCES_CHOICE = Yes
    KIND = REVERSE
    ORIENTED -> Tester_3_FAILED
Note: Bottom
Tester_3_FAILED: Junction
    -> Bottom_2
PythonCaller
    NEW_ATTRIBUTES = __ssc.id
    PYTHONSOURCE:
      # 2016-09-16, Takashi Iijima, Original Implementation

      import fme
      import fmeobjects

      class OutershellChopper(object):
          def input(self, feature):
              flag = int(feature.getAttribute('__ssc.flag'))
              self.chopped = []
              self.chop(feature.getGeometry())
              segs = {}
              for line in self.chopped:
                  coords = sorted([p.getXYZ() for p in line.getPoints()])
                  segs.setdefault((coords[0], coords[1]), []).append(line)
              for line in [s[0] for s in segs.values() if len(s) == 1]:
                  if flag < 0:
                      line.reverse()
                  feature.setGeometry(line)
                  self.pyoutput(feature)

          def chop(self, surface):
              if isinstance(surface, fmeobjects.FMEFace):
                  self.chopped += surface.getAsWireFrame()
              elif isinstance(surface, fmeobjects.FMEMesh):
                  self.chopped += surface.getAsWireFrame()
              elif isinstance(surface, fmeobjects.FMERectangleFace):
                  self.chop(surface.getAsFaceCopy())
              elif isinstance(surface, fmeobjects.FMETriangleFan):
                  for i in range(surface.numParts()):
                      self.chop(surface.getAsFaceAt(i))
              elif isinstance(surface, fmeobjects.FMETriangleStrip):
                  for i in range(surface.numParts()):
                      self.chop(surface.getAsFaceAt(i))
              elif isinstance(surface, fmeobjects.FMECompositeSurface):
                  for i in range(surface.numParts()):
                      self.chop(surface.getPartAt(i))
    PYTHONSYMBOL = OutershellChopper
    -> LineJoiner
LineJoiner
    ACCUM_ATTRS_NAME = Get Attributes From One Representative Feature
    BREAK = no
    CONSIDER_NODE_ELEVATION = yes
    GROUP_BY = __ssc.id
    LINES_AS_SEGMENTS = Yes
    PRESERVE = yes
    TOPOLOGY = End noded
    LINE -> Counter_2
Counter_2
    CNT_ATTR = __ssc.part_id
    DOMAIN = counter_part_id
    SCOPE = Local
    START = 0
    -> PathSplitter
PathSplitter
    -> PythonCaller_2
PythonCaller_2
    NEW_ATTRIBUTES = __ssc.type
    PYTHONSOURCE:
      # 2016-09-16: Takashi Iijima, Original Implementation

      import fme
      import fmeobjects
      class BRepSolidBoundaryCreator(object):
          def __init__(self):
              self.wallFaces = {}
              self.planarBoundaries = {}
              self.prevId = None
              self.feature = None

          def input(self, feature):
              id = feature.getAttribute('__ssc.id')
              if id != self.prevId:
                  self.outputSurface()
                  self.wallFaces = {}
                  self.planarBoundaries = {}
                  self.prevId = id
              partId = feature.getAttribute('__ssc.part_id')
              if partId not in self.wallFaces:
                  self.wallFaces[partId] = []
                  self.planarBoundaries[partId] = []
              v0 = feature.getCoordinate(0)
              v1 = feature.getCoordinate(1)
              if v0[0] != v1[0] or v0[1] != v1[1]:
                  z = float(feature.getAttribute('__ssc.elevation'))
                  v2 = (v1[0], v1[1], z)
                  v3 = (v0[0], v0[1], z)
                  boundary = fmeobjects.FMELine([v0, v1, v2, v3, v0])
                  self.wallFaces[partId].append(fmeobjects.FMEFace(boundary, fmeobjects.FME_CLOSE_3D_AVERAGE_MODE))
                  self.planarBoundaries[partId].append(v2)
                  self.feature = feature

          def close(self):
              self.outputSurface()

          def outputSurface(self):
              for partId in sorted(self.wallFaces.keys()):
                  wallFaces = self.wallFaces[partId]
                  planarBoundaries = self.planarBoundaries[partId]
                  if wallFaces:
                      sidewall = fmeobjects.FMECompositeSurface()
                      for face in wallFaces:
                          sidewall.appendPart(face)
                      self.feature.setGeometry(sidewall)
                      self.feature.setAttribute('__ssc.type', 'side')
                      self.pyoutput(self.feature)

                      planarBoundaries.append(planarBoundaries[0])
                      planar = fmeobjects.FMEPolygon(fmeobjects.FMELine(planarBoundaries))
                      self.feature.setGeometry(planar)
                      self.feature.setAttribute('__ssc.type', 'planar')
                      self.pyoutput(self.feature)
    PYTHONSYMBOL = BRepSolidBoundaryCreator
    -> Tester_3
Tester_3
    BOOL_OP = OR
    TEST_CLAUSE = TEST @Value(__ssc.type) = side
    TEST_MODE = Automatic
    PASSED -> Junction_5
    FAILED -> DonutBuilder
Note: Sides
Junction_5
    -> Aggregator
DonutBuilder
    ALLOW_CYCLES = No
    CONNECT_Z_MODE = First Wins
    DROP = yes
    GROUP_BY = __ssc.id
    AREA -> FaceReplacer
FaceReplacer
    ANGULAR_TOLERANCE_CHOICE = Automatic
    THICKNESS_TOLERANCE_CHOICE = Automatic
    -> Tester_4
Tester_4
    BOOL_OP = OR
    TEST_CLAUSE = TEST 0 < @Value(__ssc.flag)
    TEST_MODE = Automatic
    PASSED -> Top_2
    FAILED -> Bottom_2
Note: Tester 2: Passed
Top_2: Junction
    -> Aggregator
Note: Orientor: Oriented
Bottom_2: Junction
    -> Aggregator
Note: Output
Junction_7
    -> Junction
AttributeCreator_2
    ATTR_TABLE = SET_TO _rejected_reason = specified elevation is within zmin and zmax of seed surface
    -> Junction_3
AttributeCreator_3
    ATTR_TABLE = SET_TO _rejected_reason = unsupported geometry type
    -> Junction_3
Junction_3
    -> Inspector_2
Note: Rejected
Inspector_2
Bufferer
    ANGLE = 22.5
    CAP_STYLE = Square
    CORNER_STYLE = Miter
    MITER_LIMIT = 1
    MODE = AREA
    OFFSET = 250
ImageRasterizer
    ALPHA = 1.0
    ANTI_ALIASING = No
    BACKGROUND_ALPHA = 0.0
    BACKGROUND_COLOR = 1,1,1
    FILL_WITH_NODATA = No
    INTERPRETATION_TYPE = RGBA32
    ROWCOL_OR_CELLSIZE = CellSize
    SPECIFY_GROUND_EXTENTS = Use input data ground extents
    TOLERANCE = 0.5
    X_CELL_SIZE = 1
    Y_CELL_SIZE = 1
BuildingFootprints1-1000 (writer ESRISHAPE_8)
    attributes: GUID char(114), FORM_VALUE char(120), FUNC_VALUE char(240), POLY_GEOM_ char(20), POLY_GEO00 char(20), WAY_SEG_VA char(114), STATUS_VAL char(120), Z_ORDER_VA double, OBJECTID long
BuildingFootprints1-1000 (writer ESRISHAPE_7)
    attributes: GUID char(114), FORM_VALUE char(120), FUNC_VALUE char(240), POLY_GEOM_ char(20), POLY_GEO00 char(20), WAY_SEG_VA char(114), STATUS_VAL char(120), Z_ORDER_VA double, OBJECTID long
BuildingFootprints (writer IEPS_1)
    attributes: GUID char(114), FORM_VALUE char(120), FUNC_VALUE char(240), POLY_GEOM_CAPTURE_DATE char(20), POLY_GEOM_CHANGE_DATE char(20), WAY_SEG_VALUE char(114), STATUS_VALUE char(120), Z_ORDER_VALUE number(31,15), OBJECTID number(11,0)

Bookmark: Readers
Note: Read building footprint data
BuildingFootprints (reader FILEGDB_1)
    attributes: GUID text(114), FORM_VALUE text(120), FUNC_VALUE text(240), POLY_GEOM_CAPTURE_DATE date, POLY_GEOM_CHANGE_DATE date, WAY_SEG_VALUE text(114), STATUS_VALUE text(120), Z_ORDER_VALUE double, OBJECTID objectid
    -> GeometryExtractor
Note: Read LiDAR data
LAS (reader LAS_1)
    -> PointCloudFilter
Note: Tiles v0.4: Tiles v0 [ESRISHAPE]
Tiles v0.4 (reader ESRISHAPE_1)
    attributes: left double, top double, right double, bottom double, id long
Tiles 240m2 (reader ESRISHAPE_2)
    attributes: left double, top double, right double, bottom double, id long
Tiles 120m2 (reader ESRISHAPE_3)
    attributes: left double, top double, right double, bottom double, id long
    -> 406
Grid 500m2 (reader ESRISHAPE_4)
    attributes: left double, top double, right double, bottom double, id long
Grid 400m2 (reader ESRISHAPE_5)
    attributes: left double, top double, right double, bottom double, id long
Grid 1km2 (reader ESRISHAPE_6)
    attributes: left double, top double, right double, bottom double, id long

Bookmark: Building Footprints
Note: Geometry stored for extruding buildings in subsequent steps.
GeometryExtractor
    ATTR = _geometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> Clipper [CLIPPER]
    -> Clipper_2 [CLIPPEE]
    -> Clipper_4 [CLIPPEE]
Note: Clip point cloud with building geometry
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> PointCloudStatisticsCalculator
Note: Get Point Cloud min and median per building
PointCloudStatisticsCalculator
    POINT_COMPONENTS = "z MIN      MEDIAN  intensity        "
    -> GeometryReplacer
Note: Replace _geometry attribute
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> buildingFootprintsClipper [CLIPPEE]
Note: Tile
Junction_4
    -> buildingFootprintsClipper [CLIPPER]
buildingFootprintsClipper: Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> 3DForcer
Note: 2D -> 3D
3DForcer
    KEEPZVAL = No
    ZVALATTR = $(ELEVATION)
    -> Extruder
Note: Extrude to median heights
Extruder
    DIRECTION = Auto
    DISTANCE = (@Value(z.median))-$(ELEVATION)
    EXTRUDED -> Junction_6
Note: Output
Junction_6
    -> Junction

Bookmark: Terrain Solid Model
Aggregator
    ACCUM_ATTRS_NAME = Use Attributes From One Feature
    AGGREGATE_TYPE = Homogeneous Collection (If Possible)
    MODE = Geometry - Assemble One Level
    ORDERED = No
    SEP = ,
    AGGREGATE -> GeometryCoercer_3
GeometryCoercer_3
    GQUERY:
      for $geom in //geometry
      where $geom/count(parent::geometry) = 0
      return number($geom/@fme_id)
    KIND = fme_brep_solid
    COERCED -> Junction_7

Bookmark: Outputs
Junction
    -> STL (writer STL_1)
    -> Inspector
Note: .stl writer
STL (writer STL_1)
Note: Output inspector
Inspector
