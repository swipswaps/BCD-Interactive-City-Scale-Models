FME workspace Cork Fabrication Data Manager.fmw
Title: OSiDataTo3D

Parameters:
- DestDataset_STL_3 = /Users/mlinnane/repos/BCD-Interactive-City-Scale-Models/WIP/batch output tests   # Destination STL Folder
- ELEVATION = -8   # Planar Surface Elevation
- SourceDataset_ESRISHAPE_33 = $(FME_MF_DIR)Grids_Extents/Grid 500m2/Grid 500m2.shp   # Source Esri Shapefile(s)
- SourceDataset_ESRISHAPE_27 = /Users/mlinnane/Documents/github/BCD-Interactive-Architectural-City-Models/Grids/Grid 400m2/Grid 400m2.shp   # Source Esri Shapefile(s)
- SourceDataset_ESRISHAPE_25 = $(FME_MF_DIR)Grids_Extents/Grid 250m2   # Source Esri Shapefile(s)
- SourceDataset_ESRISHAPE_21 = /Users/mlinnane/Documents/github/BCD-Interactive-Architectural-City-Models/Grids/Non-national grid/120m2/Tiles 120m2.shp   # Source Esri Shapefile(s)
- DestDataset_ESRISHAPE = /Users/mlinnane/repos/BCD-Interactive-City-Scale-Models/WIP   # Destination Esri Shapefile Folder
- SourceDataset_ESRISHAPE = $(FME_MF_DIR)Grids_Extents/Grid 240m2   # Source Esri Shapefile(s)
- SourceDataset_FILEGDB_5 = $(FME_MF_DIR)LiDAR_Footprints/DublinBuildingGrangeGormantoDocks.gdb   # File Geodatabase
- SourceDataset_ESRISHAPE_35 = $(FME_MF_DIR)Grids_Extents/Batch Output Test Grid   # Source Esri Shapefile(s)
- SourceDataset_ESRISHAPE_23 = $(FME_MF_DIR)Grids_Extents/Grid 125m2   # Source Esri Shapefile(s)
- DestDataset_OGCKML_5 = /Users/mlinnane/repos/BCD-Interactive-City-Scale-Models/WIP/Validation Tiles   # Destination Google KML File
- SourceDataset_ESRISHAPE_37 = $(FME_MF_DIR)Grids_Extents/Boundary Dublin 7x4km 1-2000   # Source Esri Shapefile(s)
- DestDataset_OBJ = /Users/mlinnane/repos/BCD-3D-Print-Master-Files/Cork   # Destination OBJ Folder
- SourceDataset_ESRISHAPE_34 = $(FME_MF_DIR)Validation/Repaired Bridges/Repaired Bridges.shp   # Source Esri Shapefile(s)
- SourceDataset_ESRISHAPE_26 = $(FME_MF_DIR)Validation/Liffey Box/Liffey Box.shp   # Source Esri Shapefile(s)
- SourceDataset_CSV2 = $(FME_MF_DIR)Validation/Repair List.csv   # Source CSV (Comma Separated Value) File(s)
- SourceDataset_ESRISHAPE_22 = $(FME_MF_DIR)Validation/test patch/test patch.shp   # Source Esri Shapefile(s)
- SourceDataset_ESRISHAPE_28 = $(FME_MF_DIR)Grids_Extents/Sea/Sea.shp   # Source Esri Shapefile(s)
- SourceDataset_CSV2_7 = $(FME_MF_DIR)Validation/Core Artificial Poly Attribute Filter.csv   # Source CSV (Comma Separated Value) File(s)
- SourceDataset_ESRISHAPE_32 = $(FME_MF_DIR)Grids_Extents/Circle/Circle.shp   # Source Esri Shapefile(s)
- SourceDataset_ESRISHAPE_24 = $(FME_MF_DIR)Validation/Repaired Features/Repaired Features.shp   # Source Esri Shapefile(s)
- SourceDataset_FILEGDB_4 = $(FME_MF_DIR)LiDAR_Footprints/CorkCity.gdb.zip   # File Geodatabase
- SourceDataset_LAS_6 = ""$(FME_MF_DIR)LiDAR_Footprints/Cork_Clipped_PointCloud/a_FCIR_Thinned_20170617_150504.las" "$(FME_MF_DIR)LiDAR_Footprints/Cork_Clipped_PointCloud/a_FCIR_Thinned_20170617_152831.las" "$(FME_MF_DIR)LiDAR_Footprints/Cork_Clipped_PointCloud/a_FCIR_Thinned_20170620_142601.las" "$(FME_MF_DIR)LiDAR_Footprints/Cork_Clipped_PointCloud/b_FCIR_Thinned_20170617_150504.las" "$(FME_MF_DIR)LiDAR_Footprints/Cork_Clipped_PointCloud/b_FCIR_Thinned_20170617_152831.las" "$(FME_MF_DIR)LiDAR_Footprints/Cork_Clipped_PointCloud/b_FCIR_Thinned_20170620_142601.las""   # Source ASPRS LAS File(s)
- SourceDataset_LAS_5 = $(FME_MF_DIR)LiDAR_Footprints/Cork_DTM/LiDAR_Hackathon_Cork_2m_DTM.las   # Source ASPRS LAS File(s)
- SourceDataset_ESRISHAPE_36 = $(FME_MF_DIR)Grids_Extents/Cork Tiles/Cork Tiles.shp   # Source Esri Shapefile(s)
- SourceDataset_CSV2_5 = $(FME_MF_DIR)Validation/Water Exceptions List.csv   # Source CSV (Comma Separated Value) File(s)
- SourceDataset_ESRISHAPE_29 = $(FME_MF_DIR)Grids_Extents/River Environs/River Environs.shp   # Source Esri Shapefile(s)
- SourceDataset_ESRISHAPE_20 = $(FME_MF_DIR)Grids_Extents/Grid 0.5km/Grid 0.5km.shp   # Source Esri Shapefile(s)

Readers:
- ESRISHAPE_1: ESRISHAPE from $(SourceDataset_ESRISHAPE_33)
- ESRISHAPE_2: ESRISHAPE from $(SourceDataset_ESRISHAPE_27)
- ESRISHAPE_3: ESRISHAPE from $(SourceDataset_ESRISHAPE_25) in EPSG:2157
- ESRISHAPE_4: ESRISHAPE from $(SourceDataset_ESRISHAPE_21)
- ESRISHAPE_5: ESRISHAPE from $(SourceDataset_ESRISHAPE_23) in EPSG:2157
- ESRISHAPE_6: ESRISHAPE from $(SourceDataset_ESRISHAPE)
- FILEGDB_1: FILEGDB from $(SourceDataset_FILEGDB_5)
- ESRISHAPE_7: ESRISHAPE from $(SourceDataset_ESRISHAPE_35) in EPSG:2157
- ESRISHAPE_8: ESRISHAPE from $(SourceDataset_ESRISHAPE_37)
- ESRISHAPE_9: ESRISHAPE from $(SourceDataset_ESRISHAPE_34)
- ESRISHAPE_10: ESRISHAPE from $(SourceDataset_ESRISHAPE_26)
- CSV2_1: CSV2 from $(SourceDataset_CSV2)
- ESRISHAPE_11: ESRISHAPE from $(SourceDataset_ESRISHAPE_24)
- ESRISHAPE_12: ESRISHAPE from $(SourceDataset_ESRISHAPE_22)
- ESRISHAPE_13: ESRISHAPE from $(SourceDataset_ESRISHAPE_28)
- CSV2_2: CSV2 from $(SourceDataset_CSV2_7)
- ESRISHAPE_14: ESRISHAPE from $(SourceDataset_ESRISHAPE_32)
- FILEGDB_2: FILEGDB from $(SourceDataset_FILEGDB_4)
- LAS_1: LAS from $(SourceDataset_LAS_6)
- LAS_2: LAS from $(SourceDataset_LAS_5)
- ESRISHAPE_15: ESRISHAPE from $(SourceDataset_ESRISHAPE_36) in EPSG:2157
- CSV2_3: CSV2 from $(SourceDataset_CSV2_5)
- ESRISHAPE_16: ESRISHAPE from $(SourceDataset_ESRISHAPE_29)
- ESRISHAPE_17: ESRISHAPE from $(SourceDataset_ESRISHAPE_20)

Writers:
- STL_1: STL to $(DestDataset_STL_3)
- ESRISHAPE_18: ESRISHAPE to $(DestDataset_ESRISHAPE)
- OGCKML_1: OGCKML to $(DestDataset_OGCKML_5) in EPSG:2157
- OBJ_1: OBJ to $(DestDataset_OBJ)

AttributeFilter_4
    ATTR_NAME = OBJECTID
    ATTR_VALUES = <Empty>,<Missing>,<Null>,<Unfiltered>,6152,6155
    6152 -> Clip_Buildings [CLIPPEE]
    6155 -> Clip_Buildings [CLIPPEE]
Note: DTM
Junction_19
    -> Clipper_7 [CLIPPEE]
    -> Clipper_2 [CLIPPEE]
    -> Tile_out_DTM [CLIPPEE]
    -> SurfaceModeller_2 [POINTS/LINES]
    -> Inspector_3
Junction_4
    -> Junction_15
Note: Grid/Tile
Junction_15
    -> tileClipper [CLIPPER]
    -> Clipper_10 [CLIPPER]
    -> 3DForcer_6
    -> Bufferer
    -> Clipper_4 [CLIPPEE]
Inspector_3
Note: DTM clipped by tile and buffered tile
Tile_out_DTM: Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> SurfaceModeller [POINTS/LINES]
Core Artificial Poly Attribute Filter (reader CSV2_2)
    attributes: OBJECTID string
    -> FeatureMerger_3 [REQUESTOR]
FeatureMerger_3
    ATTR_ACCUM_MODE = Merge Supplier
    ATTR_CONFLICT_RES = Use Requestor
    IGNORE_NULLS = No
    JOIN_KEYS = @Value(OBJECTID) @Value(OBJECTID) AUTO
    MERGE_TYPE = Attributes Only
    PROCESS_DUPS = NO
    REJECT_NULL_MISSING_KEYS = No
    SUPPLIERS_FIRST = No
    USED_SUPPLIER -> Clip_Buildings [CLIPPEE]
CSV (reader CSV2_1)
    attributes: repair_id2 string, repair_id string, OBJECT ID string, Notes string
    -> FeatureMerger [SUPPLIER]
FeatureMerger
    ATTR_ACCUM_MODE = Merge Supplier
    ATTR_CONFLICT_RES = Use Requestor
    IGNORE_NULLS = No
    JOIN_KEYS = @Value(OBJECTID) @Value(OBJECT ID) AUTO
    MERGE_TYPE = Attributes Only
    PROCESS_DUPS = NO
    REJECT_NULL_MISSING_KEYS = No
    SUPPLIERS_FIRST = No
    UNMERGED_REQUESTOR -> Clip_Buildings [CLIPPEE]
AttributeManager
    ATTR_TABLE = SET_TO z.median = FME_CONDITIONAL:DEFAULT_VALUE'_FME_NO_OP_'BOOL_OP;OR;COMPOSITE_TEST;1;TEST @Value(repair_id2) = B3_2B'50'BOOL_OP;OR;COMPOSITE_TEST;1;TEST @Value(repair_id2) = C1_2E'175'BOOL_OP;OR;COMPOSITE_TEST;1;TEST @Value(OBJECTID) = 16061'@Value(z.median) + 3.5'BOOL_OP;OR;COMPOSITE_TEST;1;TEST @Value(OBJECTID) = 16066'@Value(z.median) + 3.5'BOOL_OP;OR;COMPOSITE_TEST;1;TEST @Value(OBJECTID) = 16077'@Value(z.median) + 3.5'BOOL_OP;OR;COMPOSITE_TEST;1;TEST @Value(OBJECTID) = 15869'@Value(z.median) + 3.5'BOOL_OP;OR;COMPOSITE_TEST;1;TEST @Value(OBJECTID) = 20650'@Value(z.median) + 1.5'BOOL_OP;OR;COMPOSITE_TEST;1;TEST @Value(OBJECTID) = 16055'@Value(z.median) + 3.5'BOOL_OP;OR;COMPOSITE_TEST;1;TEST @Value(OBJECTID) = 20663'@Value(z.median) + 3.5'BOOL_OP;OR;COMPOSITE_TEST;1;TEST @Value(OBJECTID) = 16051'@Value(z.median) + 3.5'BOOL_OP;OR;COMPOSITE_TEST;1;TEST @Value(OBJECTID) = 16298'@Value(z.median) + 3.5'BOOL_OP;OR;COMPOSITE_TEST;1;TEST @Value(repair_id2) = C2_7A'@Value(z.median) + 20'BOOL_OP;OR;COMPOSITE_TEST;1;TEST @Value(repair_id2) = D1_3A'@Value(z.median) + 22'BOOL_OP;OR;COMPOSITE_TEST;1;TEST @Value(OBJECTID) = 21826'@Value(z.median) + 3'BOOL_OP;OR;COMPOSITE_TEST;1;TEST @Value(repair_id2) = D2_1B'@Value(z.median) + 28'BOOL_OP;OR;COMPOSITE_TEST;1;TEST @Value(repair_id2) = D2_1A'@Value(z.median) + 37'BOOL_OP;OR;COMPOSITE_TEST;1;TEST @Value(repair_id2) = D2_1D'@Value(z.median) + 4'BOOL_OP;OR;COMPOSITE_TEST;1;TEST @Value(repair_id2) = D2_4B'@Value(z.median) + 30'BOOL_OP;OR;COMPOSITE_TEST;1;TEST @Value(repair_id2) = D2_8B'@Value(z.median) + 8'BOOL_OP;OR;COMPOSITE_TEST;1;TEST @Value(repair_id2) = D2_9C'@Value(z.median) + 4'BOOL_OP;OR;COMPOSITE_TEST;1;TEST @Value(repair_id2) = D2_13'@Value(z.median) + 3'BOOL_OP;OR;COMPOSITE_TEST;1;TEST @Value(repair_id2) = D2_16F'@Value(z.median) + 35'BOOL_OP;OR;COMPOSITE_TEST;1;TEST @Value(repair_id2) = D2_19B'@Value(z.median) + 30'BOOL_OP;OR;COMPOSITE_TEST;1;TEST @Value(repair_id2) = D3_1C'@Value(z.median) + 16'BOOL_OP;OR;COMPOSITE_TEST;1;TEST @Value(repair_id2) = D3_4C'@Value(z.median) + 13'BOOL_OP;OR;COMPOSITE_TEST;1;TEST @Value(repair_id2) = D3_9D'@Value(z.median) + 10'BOOL_OP;OR;COMPOSITE_TEST;1;TEST @Value(repair_id2) = D3_10E'@Value(z.median) + 6'BOOL_OP;OR;COMPOSITE_TEST;1;TEST @Value(repair_id2) = D4_1R'@Value(z.median) + 7'BOOL_OP;OR;COMPOSITE_TEST;1;TEST @Value(repair_id2) = E2_2E'@Value(z.median) + 10'BOOL_OP;OR;COMPOSITE_TEST;1;TEST @Value(repair_id2) = E2_4E'@Value(z.median) + 24'BOOL_OP;OR;COMPOSITE_TEST;1;TEST @Value(repair_id2) = E2_5B'@Value(z.median) + 32'BOOL_OP;OR;COMPOSITE_TEST;1;TEST @Value(repair_id2) = E2_5E'@Value(z.median) + 37'BOOL_OP;OR;COMPOSITE_TEST;1;TEST @Value(repair_id2) = E3_6C'@Value(z.median) + 50'BOOL_OP;OR;COMPOSITE_TEST;1;TEST @Value(repair_id2) = E3_7C'@Value(z.median) - 10'BOOL_OP;OR;COMPOSITE_TEST;1;TEST @Value(repair_id2) = E3_7B'@Value(z.median) - 10'BOOL_OP;OR;COMPOSITE_TEST;1;TEST @Value(repair_id2) = E3_8B'@Value(z.median) - 28'BOOL_OP;OR;COMPOSITE_TEST;1;TEST @Value(repair_id2) = E3_8A'@Value(z.median) - 10'BOOL_OP;OR;COMPOSITE_TEST;1;TEST @Value(repair_id2) = E3_8C'@Value(z.median) - 28'BOOL_OP;OR;COMPOSITE_TEST;1;TEST @Value(repair_id2) = E3_10A'@Value(z.median) - 13'BOOL_OP;OR;COMPOSITE_TEST;1;TEST @Value(OBJECTID) = 29217'@Value(z.median) - 17'BOOL_OP;OR;COMPOSITE_TEST;1;TEST @Value(repair_id2) = F2_1B'@Value(z.median) + 72'BOOL_OP;OR;COMPOSITE_TEST;1;TEST @Value(repair_id2) = F2_1N'@Value(z.median) + 65'BOOL_OP;OR;COMPOSITE_TEST;1;TEST @Value(repair_id2) = F2_1F'@Value(z.median) + 10'BOOL_OP;OR;COMPOSITE_TEST;1;TEST @Value(repair_id2) = G1_1A'@Value(z.median) + 6'BOOL_OP;OR;COMPOSITE_TEST;1;TEST @Value(repair_id2) = G3_1B'@Value(z.median) - 4'FME_NUM_CONDITIONS46___
    -> 3DForcer_8
    -> 3DForcer_4
Note: Geometry stored for extruding buildings in subsequent steps.
GeometryExtractor_4
    ATTR = _geometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> Clipper_2 [CLIPPER]
Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> PointCloudStatisticsCalculator_4
PointCloudStatisticsCalculator_4
    POINT_COMPONENTS = "z MIN        intensity        "
    -> GeometryReplacer_3
Note: Replace _geometry attribute
GeometryReplacer_3
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> AttributeFilter_6
AttributeFilter_6
    ATTR_NAME = repair_id
    ATTR_VALUES = <Empty>,<Missing>,<Null>,<Unfiltered>,1102,1107,1108,1111,1114
    1102 -> 3DForcer_2
    1107 -> 3DForcer_17
    1108 -> 3DForcer_16
    1111 -> 3DForcer_14
    1114 -> 3DForcer_11
Note: Output
Junction_18
    -> Junction_14 [off]

Bookmark: Rounded Grid Cell Corners
Circle (reader ESRISHAPE_14)
    attributes: id long
    -> Clipper_6 [CLIPPEE]
Grid 0.5km (reader ESRISHAPE_17)
    attributes: left double, top double, right double, bottom double, id long
    -> AttributeFilter_5
AttributeFilter_5
    ATTR_NAME = id
    ATTR_VALUES = <Empty>,<Missing>,<Null>,<Unfiltered>,553,560,943,950
    553 -> Clipper_3 [CLIPPER]
    553 -> Clipper_6 [CLIPPER]
    560 -> Clipper_3 [CLIPPER]
    560 -> Clipper_6 [CLIPPER]
    943 -> Clipper_3 [CLIPPER]
    943 -> Clipper_6 [CLIPPER]
    950 -> Clipper_3 [CLIPPER]
    950 -> Clipper_6 [CLIPPER]
Clipper_6
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> Dissolver
AttributeFilter_7
    ATTR_NAME = id
    ATTR_VALUES = <Empty>,<Missing>,<Null>,<Unfiltered>,1,4,25,28
    1 -> Clipper_3 [CLIPPEE]
    4 -> Clipper_3 [CLIPPEE]
    25 -> Clipper_3 [CLIPPEE]
    28 -> Clipper_3 [CLIPPEE]
Clipper_3
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    OUTSIDE -> Dissolver
Dissolver
    ACCUM_INPUT_ATTRS = Use Attributes From One Feature
    CLEANING_TOLERANCE = Automatic
    CONNECT_Z_MODE = First Wins
    DEAGGREGATE_INPUT = Yes
    AREA -> Junction_4

Bookmark: Readers
BUILDING_GROUP_POLY (reader FILEGDB_2)
    attributes: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
RAIL_NETWORK_SEGMENT_LINE (reader FILEGDB_2)
    attributes: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
Note: 2009 BuildingFootprints
BuildingFootprints (reader FILEGDB_1)
    attributes: GUID text(114), FORM_VALUE text(120), FUNC_VALUE text(240), POLY_GEOM_CAPTURE_DATE date, POLY_GEOM_CHANGE_DATE date, WAY_SEG_VALUE text(114), STATUS_VALUE text(120), Z_ORDER_VALUE double, OBJECTID objectid
ARTIFICIAL_POLY (reader FILEGDB_2)
    attributes: GUID text(114), FORM_VALUE text(120), FUNC_VALUE text(240), ENG_NAME_VALUE text(750), STATUS_VALUE text(120), Z_ORDER_VALUE double, OBJECTID objectid
    -> FeatureMerger_3 [SUPPLIER]
BUILDING_POLY (reader FILEGDB_2)
    attributes: GUID text(114), FORM_VALUE text(120), FUNC_VALUE text(240), ENG_NAME_VALUE text(750), STATUS_VALUE text(120), Z_ORDER_VALUE double, ADDR_GEO_CODE_1 text(150), ADDR_GEO_CODE_2 text(150), ADDR_NAT_POST_CODE text(150), WAY_SEG_VALUE text(114), BLD_NO_VALUE text(750), OBJECTID objectid
    -> FeatureMerger [REQUESTOR]
SITE_POLY (reader FILEGDB_2)
    attributes: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
VEGETATION_POLY (reader FILEGDB_2)
    attributes: GUID text(114), FORM_VALUE text(120), FUNC_VALUE text(240), ENG_NAME_VALUE text(750), STATUS_VALUE text(120), Z_ORDER_VALUE double, ADDR_GEO_CODE_1 text(150), ADDR_GEO_CODE_2 text(150), ADDR_NAT_POST_CODE text(150), WAY_SEG_VALUE text(114), BLD_NO_VALUE text(750), OBJECTID objectid
    -> AttributeFilter_4
WATER_LINE (reader FILEGDB_2)
    attributes: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
WAY_GDF2 (reader FILEGDB_2)
    attributes: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
WAY_POLY (reader FILEGDB_2)
    attributes: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
Boundary Dublin 7x4km 1-2000 (reader ESRISHAPE_8)
    attributes: left double, top double, right double, bottom double, id long
    -> Junction_4 [off]
Batch Output Test Grid (reader ESRISHAPE_7)
    attributes: left double, top double, right double, bottom double, id long
Repaired Features (reader ESRISHAPE_11)
    attributes: id long, repair_id char(5), repair_id2 char(7)
    -> Clip_Buildings [CLIPPEE]
River Environs (reader ESRISHAPE_16)
    attributes: id long
    -> Junction_15 [off]
125m2 (reader ESRISHAPE_5)
    attributes: left double, top double, right double, bottom double, id long
    -> AttributeFilter_2
Tiles 240m2 (reader ESRISHAPE_6)
    attributes: left double, top double, right double, bottom double, id long
250m2 (reader ESRISHAPE_3)
    attributes: left double, top double, right double, bottom double, id long
Grid 400m2 (reader ESRISHAPE_2)
    attributes: left double, top double, right double, bottom double, id long
Grid 500m2 (reader ESRISHAPE_1)
    attributes: left double, top double, right double, bottom double, id long
Cork Tiles (reader ESRISHAPE_15)
    attributes: left double, top double, right double, bottom double, id long
    -> AttributeFilter
    -> AttributeFilter_7
Liffey Box (reader ESRISHAPE_10)
    attributes: id long
    -> Junction_4 [off]
test patch (reader ESRISHAPE_12)
    attributes: id long
    -> Junction_4 [off]

Bookmark: Point CLouds
Note: Clipped Point Cloud
LAS (reader LAS_1)
    -> Clipper_8 [CLIPPEE]
Note: DTM
LAS (reader LAS_2)
    -> Junction_19

Bookmark: 125m2 Grid filter
AttributeFilter_2
    ATTR_NAME = id
    ATTR_VALUES = <Empty>,<Missing>,<Null>,<Unfiltered>,27330
    27330 -> Junction_4 [off]

Bookmark: Print Tiles filter
AttributeFilter
    ATTR_NAME = id
    ATTR_VALUES = <Empty>,<Missing>,<Null>,<Unfiltered>,1,2,3,4,5,6,7,8,9,10,11,12,13,14,15,16,17,18,19,20,21,22,23,24,25,26,27,28
    2 -> Junction_4
    3 -> Junction_4
    5 -> Junction_4
    6 -> Junction_4
    7 -> Junction_4
    8 -> Junction_4
    9 -> Junction_4
    10 -> Junction_4
    11 -> Junction_4
    12 -> Junction_4
    13 -> Junction_4
    14 -> Junction_4
    15 -> Junction_4
    16 -> Junction_4
    17 -> Junction_4
    18 -> Junction_4
    19 -> Junction_4
    20 -> Junction_4
    21 -> Junction_4
    22 -> Junction_4
    23 -> Junction_4
    24 -> Junction_4
    26 -> Junction_4
    27 -> Junction_4

Bookmark: Clip features with buffered model boundary
Note: Add buffer around boundary
Bufferer
    ANGLE = 22.5
    CAP_STYLE = None
    CORNER_STYLE = Round
    MODE = AREA
    OFFSET = 125
    BUFFERED -> Clip_Buildings [CLIPPER]
    BUFFERED -> Tile_out_DTM [CLIPPER]
    BUFFERED -> Inspector_3
Note: Clip features with buffered model boundary
Clip_Buildings: Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> GeometryExtractor_2

Bookmark: Base
3DForcer_6
    KEEPZVAL = No
    ZVALATTR = -3
    -> Extruder_4
Extruder_4
    DIRECTION = Vertical
    DISTANCE = 0.5
    EXTRUDED -> Junction_17

Bookmark: Feature Merging
Note: Base
Junction_17
    -> Junction_10
Note: Extrusion z.min -> z.median
Junction_12
    -> Junction_10
Note: Terrain
Junction_9
    -> Junction_10
Note: Water
Junction_8
    -> Junction_10
Junction_10
    -> 3DRotator
Note: Extrusion to below surface
Junction_14
    -> 3DRotator [off]
Note: Rotate to correct orientation
3DRotator
    ANGLE = -90
    AXIS_CHOICE = X Axis
    ROTATED -> Cork Master_low poly terrain4 (writer OBJ_1)
    ROTATED -> Inspector

Bookmark: PointCloud Statistics
Note: Geometry stored for extruding buildings in subsequent steps.
GeometryExtractor_2
    ATTR = _geometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> Clipper_8 [CLIPPER]
    -> Clipper_7 [CLIPPER]
Note: Clip point cloud with building geometry
Clipper_8
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> PointCloudStatisticsCalculator_2
    INSIDE -> Clipper_10 [CLIPPEE]
PointCloudStatisticsCalculator_2
    POINT_COMPONENTS = "z       MEDIAN  intensity        "
    -> Aggregator_2
Clipper_7
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> PointCloudStatisticsCalculator_3
PointCloudStatisticsCalculator_3
    POINT_COMPONENTS = "z MIN        intensity        "
    -> Aggregator_2
Aggregator_2
    ACCUM_ATTRS_NAME = Merge Incoming Attributes
    GROUP_BY = repair_id2 GUID repair_id
    MODE = Attributes Only
    SEP = ,
    AGGREGATE -> GeometryReplacer
Note: Replace _geometry attribute
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> tileClipper [CLIPPEE]
Note: Clip with tile
tileClipper: Clipper
    ATTR_ACCUM_MODE = Merge Clipper
    ATTR_CONFLICT_RES = Use Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> 3DForcer_3
    INSIDE -> 3DForcer
    INSIDE -> AttributeManager

Bookmark: PointCLoud clipped by tile and building
Clipper_10
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only

Bookmark: Building Extrusion
Note: 2D -> 3D
3DForcer_8
    KEEPZVAL = No
    ZVALATTR = -5
    -> Extruder_7
Note: Extrude to median heights
Extruder_7
    DIRECTION = Vertical
    DISTANCE = @Value(z.median)-(-5)
    EXTRUDED -> Junction_13
Note: Output
Junction_13
    -> Junction_14
Note: 2D -> 3D
3DForcer_3
    KEEPZVAL = No
    ZVALATTR = @Value(z.min)
    -> Extruder_3
Note: Extrude to median heights
Extruder_3
    DIRECTION = Vertical
    DISTANCE = @Value(z.median)-@Value(z.min)
    EXTRUDED -> Junction_11
Note: Output
Junction_11
    -> Junction_12
Note: 2D -> 3D
3DForcer
    KEEPZVAL = No
    ZVALATTR = $(ELEVATION)
    -> Extruder
Note: Extrude to median heights
Extruder
    DIRECTION = Auto
    DISTANCE = (@Value(z.median))-$(ELEVATION)
    EXTRUDED -> Junction_6
Note: Output
Junction_6

Bookmark: Prep for KML
Note: 2D -> 3D
3DForcer_4
    KEEPZVAL = No
    ZVALATTR = @Value(z.median)
    -> KMLPropertySetter
KMLPropertySetter
    ADD_ATTR_TABLE = Yes
    ALTITUDE_MODE = Absolute
    ATTR_TABLE_TITLE = Attributes
    CONTENT_TYPE = Text
    EXTRUDE = Yes
    GEOM_TYPE = Vector
    NAME = <auto>
    SUMMARY = <none>
    TESSELATE = Yes
    VISIBILITY = Yes
    -> KML (writer OGCKML_1)

Bookmark: Outputs
KML (writer OGCKML_1)
Note: .obj writer
Cork Master_low poly terrain4 (writer OBJ_1)
Note: Output inspector
Inspector
Note: .stl writer
Print 0.6.2 Tile 14 DTM Unthinned Surface Tolerance 0.165 Aggregate No river no rail (writer STL_1)

Bookmark: Water Surface
WATER_POLY (reader FILEGDB_2)
    attributes: GUID text(114), FORM_VALUE text(120), FUNC_VALUE text(240), ENG_NAME_VALUE text(750), STATUS_VALUE text(120), Z_ORDER_VALUE double, ADDR_GEO_CODE_1 text(150), ADDR_GEO_CODE_2 text(150), ADDR_NAT_POST_CODE text(150), WAY_SEG_VALUE text(114), BLD_NO_VALUE text(750), OBJECTID objectid
    -> FeatureMerger_2 [REQUESTOR]
Sea (reader ESRISHAPE_13)
    attributes: id long, repair_id2 char(7)
    -> Clipper [CLIPPEE]
CSV (reader CSV2_3)
    attributes: OBJECTID string
    -> FeatureMerger_2 [SUPPLIER]
FeatureMerger_2
    ATTR_ACCUM_MODE = Merge Supplier
    ATTR_CONFLICT_RES = Use Requestor
    IGNORE_NULLS = No
    JOIN_KEYS = @Value(OBJECTID) @Value(OBJECTID) AUTO
    MERGE_TYPE = Attributes Only
    PROCESS_DUPS = NO
    REJECT_NULL_MISSING_KEYS = No
    SUPPLIERS_FIRST = No
    UNMERGED_REQUESTOR -> AttributeFilter_3
Note: Filter out all water features that lie under bridges etc.
AttributeFilter_3
    ATTR_NAME = Z_ORDER_VALUE
    ATTR_VALUES = <Empty>,<Missing>,<Null>,<Unfiltered>,-1
    <UNFILTERED> -> SurfaceModeller_2 [DRAPE_FEATURES]
SurfaceModeller_2
    CONTOUR_DIMENSION = 3
    CONTOUR_INTERVAL = 100.0
    DRAPE_TYPE = MODEL
    ELEV_ATTR = _elevation
    IGNORE_INPUT_ON_INTERVAL = Perturb Input Points On Contour Interval
    INTERPOLATION_TYPE = AUTO
    NODATA_VALUE = -32767.0
    TOLERANCE = 40
    X_SPACING = 100.0
    Y_SPACING = 100.0
    DRAPED_FEATURES -> GeometryExtractor_3
GeometryExtractor_3
    ATTR = _watergeometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> BoundsExtractor_2
BoundsExtractor_2
    XMAX = _xmax
    XMIN = _xmin
    YMAX = _ymax
    YMIN = _ymin
    ZMAX = _zmax
    ZMIN = _zmin
    -> StatisticsCalculator
StatisticsCalculator
    COMPUTE_HISTOGRAM = NO
    COUNT_ATTR = _count
    MAX_ATTR = _max
    MEAN_ATTR = _mean
    MIN_ATTR = _min
    PREPEND_ATTR_NAME_CHOICE = For multiple results only
    STATS_ATTRS = _zmin
    SUM_ATTR = _sum
    COMPLETE -> GeometryReplacer_2
GeometryReplacer_2
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_watergeometry)
    SRS_AXIS_ORDER_DISPLAY = Automatic
    -> Clipper_4 [CLIPPER]
Note: Tile out water features
Clipper_4
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> 3DForcer_5
    OUTSIDE -> SurfaceModeller [DRAPE_FEATURES]
3DForcer_5
    KEEPZVAL = No
    ZVALATTR = @Value(_zmin)
    -> AttributeFilter_9
AttributeFilter_9
    ATTR_NAME = OBJECTID
    ATTR_VALUES = <Empty>,<Missing>,<Null>,<Unfiltered>,259,437,137,453,90,96,148
    <MISSING> -> Offsetter
    <UNFILTERED> -> Offsetter
    259 -> Offsetter_2
    437 -> Offsetter_3
    137 -> Offsetter_4
    453 -> Offsetter_5
    90 -> Offsetter_6
    96 -> Offsetter_7
    148 -> Offsetter_8
Offsetter
    MODE = Cartesian Coordinate
    XOFF = 0
    YOFF = 0
    ZOFF = -1
    OFFSET -> Extruder_6
Extruder_6
    DIRECTION = Vertical
    DISTANCE = -0.5
    EXTRUDED -> Junction_2
Offsetter_2
    MODE = Cartesian Coordinate
    XOFF = 0
    YOFF = 0
    ZOFF = 0
    OFFSET -> Extruder_2
Extruder_2
    DIRECTION = Vertical
    DISTANCE = -0.5
    EXTRUDED -> Junction_2
Offsetter_3
    MODE = Cartesian Coordinate
    XOFF = 0
    YOFF = 0
    ZOFF = -2.5
    OFFSET -> Extruder_9
Extruder_9
    DIRECTION = Vertical
    DISTANCE = -0.5
    EXTRUDED -> Junction_2
Offsetter_4
    MODE = Cartesian Coordinate
    XOFF = 0
    YOFF = 0
    ZOFF = 0
    OFFSET -> Extruder_8
Extruder_8
    DIRECTION = Vertical
    DISTANCE = -0.5
    EXTRUDED -> Junction_2
Offsetter_5
    MODE = Cartesian Coordinate
    XOFF = 0
    YOFF = 0
    ZOFF = -3.25
    OFFSET -> Extruder_18
Extruder_18
    DIRECTION = Vertical
    DISTANCE = -0.5
    EXTRUDED -> Junction_2
Offsetter_6
    MODE = Cartesian Coordinate
    XOFF = 0
    YOFF = 0
    ZOFF = -3.25
    OFFSET -> Extruder_19
Extruder_19
    DIRECTION = Vertical
    DISTANCE = -0.5
    EXTRUDED -> Junction_2
Offsetter_7
    MODE = Cartesian Coordinate
    XOFF = 0
    YOFF = 0
    ZOFF = 2.5
    OFFSET -> Extruder_20
Extruder_20
    DIRECTION = Vertical
    DISTANCE = -0.5
    EXTRUDED -> Junction_2
Offsetter_8
    MODE = Cartesian Coordinate
    XOFF = 0
    YOFF = 0
    ZOFF = -3.7
    OFFSET -> Extruder_21
Extruder_21
    DIRECTION = Vertical
    DISTANCE = -0.5
    EXTRUDED -> Junction_2
Junction_2
    -> Junction_8
Note: Bridges missing in Prime2
Repaired Bridges (reader ESRISHAPE_9)
    attributes: id long
    -> Clipper [CLIPPER]
Note: Filter out bridges missing in Prime2
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only

Bookmark: Surface Drape
Note: Build surface model / Drape clipping boundary / Output triangles / https://knowledge.safe.com/articles/1310/how-to-clip-tin-surfaces.html
SurfaceModeller
    CONTOUR_DIMENSION = 3
    CONTOUR_INTERVAL = 100.0
    DRAPE_TYPE = MODEL
    ELEV_ATTR = _elevation
    IGNORE_INPUT_ON_INTERVAL = Perturb Input Points On Contour Interval
    INTERPOLATION_TYPE = AUTO
    NODATA_VALUE = -32767.0
    TOLERANCE = 0.165
    X_SPACING = 100.0
    Y_SPACING = 100.0
    DRAPED_FEATURES -> Clipper_5 [CLIPPER]
    TRIANGLES -> Clipper_5 [CLIPPEE]
Note: Clip triangles by boundary
Clipper_5
    BOUNDARY_CASES = Treat as Outside
    CLIP_TYPE = Multiple Clippers
    CREATE_AGGREGATES = Yes
    MERGE_ATTRS = No
    PRESERVE_CLIPPEE_EXTENTS = No
    INSIDE -> FaceReplacer_3
    CLIPPED_INSIDE -> FaceReplacer_3
Note: Replace polygons with faces
FaceReplacer_3
    CHECK_PLANARITY = No
    PLANARITY_TOLERANCE = 0.0
    -> AggregateFilter

Bookmark: Taksahi Flow creates base by creating side and bottom faces from terrain surface
AggregateFilter
    AGGREGATE -> AttributeCreator_3
    NOT_AGGREGATE -> GeometryFilter
GeometryFilter
    BREAK_AGG = No
    GEOM_PORT_NAMES = Surface
    SURFACE -> BoundsExtractor
    <UNFILTERED> -> AttributeCreator_3
BoundsExtractor
    ZMAX = __ssc.zmax
    ZMIN = __ssc.zmin
    -> AttributeCreator
AttributeCreator
    ATTR_TABLE:
      SET_TO __ssc.elevation = $(ELEVATION)
      SET_TO __ssc.flag = FME_CONDITIONAL:DEFAULT_VALUE'0'BOOL_OP;OR;COMPOSITE_TEST;<Unused>;TEST $(ELEVATION) < @Value(__ssc.zmin)'-1'BOOL_OP;OR;COMPOSITE_TEST;<Unused>;TEST @Value(__ssc.zmax) < $(ELEVATION)'1'FME_NUM_CONDITIONS3___
    -> Tester
Tester
    BOOL_OP = OR
    COMPOSITE_TEST = 1
    TEST_CLAUSE = TEST @Value(__ssc.flag) != 0
    TEST_MODE = TEST
    PASSED -> Counter
    FAILED -> AttributeCreator_2
Counter
    CNT_ATTR = __ssc.id
    DOMAIN = counter_id
    SCOPE = Local
    START = 0
    -> PythonCaller
    -> Tester_2
Tester_2
    BOOL_OP = OR
    TEST_CLAUSE = TEST @Value(__ssc.flag) < 0
    TEST_MODE = Automatic
    PASSED -> Tester_3_PASSED
    FAILED -> Orientor
Note: Top
Tester_3_PASSED: Junction
    -> Top_2
Orientor
    FLIP_APPEARANCES_CHOICE = Yes
    KIND = REVERSE
    ORIENTED -> Tester_3_FAILED
Note: Bottom
Tester_3_FAILED: Junction
    -> Bottom_2 [off]
PythonCaller
    NEW_ATTRIBUTES = __ssc.id
    PYTHONSOURCE:
      # 2016-09-16, Takashi Iijima, Original Implementation

      import fme
      import fmeobjects

      class OutershellChopper(object):
          def input(self, feature):
              flag = int(feature.getAttribute('__ssc.flag'))
              self.chopped = []
              self.chop(feature.getGeometry())
              segs = {}
              for line in self.chopped:
                  coords = sorted([p.getXYZ() for p in line.getPoints()])
                  segs.setdefault((coords[0], coords[1]), []).append(line)
              for line in [s[0] for s in segs.values() if len(s) == 1]:
                  if flag < 0:
                      line.reverse()
                  feature.setGeometry(line)
                  self.pyoutput(feature)

          def chop(self, surface):
              if isinstance(surface, fmeobjects.FMEFace):
                  self.chopped += surface.getAsWireFrame()
              elif isinstance(surface, fmeobjects.FMEMesh):
                  self.chopped += surface.getAsWireFrame()
              elif isinstance(surface, fmeobjects.FMERectangleFace):
                  self.chop(surface.getAsFaceCopy())
              elif isinstance(surface, fmeobjects.FMETriangleFan):
                  for i in range(surface.numParts()):
                      self.chop(surface.getAsFaceAt(i))
              elif isinstance(surface, fmeobjects.FMETriangleStrip):
                  for i in range(surface.numParts()):
                      self.chop(surface.getAsFaceAt(i))
              elif isinstance(surface, fmeobjects.FMECompositeSurface):
                  for i in range(surface.numParts()):
                      self.chop(surface.getPartAt(i))
    PYTHONSYMBOL = OutershellChopper
    -> LineJoiner
LineJoiner
    ACCUM_ATTRS_NAME = Get Attributes From One Representative Feature
    BREAK = no
    CONSIDER_NODE_ELEVATION = yes
    GROUP_BY = __ssc.id
    LINES_AS_SEGMENTS = Yes
    PRESERVE = yes
    TOPOLOGY = End noded
    LINE -> Counter_2
Counter_2
    CNT_ATTR = __ssc.part_id
    DOMAIN = counter_part_id
    SCOPE = Local
    START = 0
    -> PathSplitter
PathSplitter
    -> PythonCaller_2
PythonCaller_2
    NEW_ATTRIBUTES = __ssc.type
    PYTHONSOURCE:
      # 2016-09-16: Takashi Iijima, Original Implementation

      import fme
      import fmeobjects
      class BRepSolidBoundaryCreator(object):
          def __init__(self):
              self.wallFaces = {}
              self.planarBoundaries = {}
              self.prevId = None
              self.feature = None

          def input(self, feature):
              id = feature.getAttribute('__ssc.id')
              if id != self.prevId:
                  self.outputSurface()
                  self.wallFaces = {}
                  self.planarBoundaries = {}
                  self.prevId = id
              partId = feature.getAttribute('__ssc.part_id')
              if partId not in self.wallFaces:
                  self.wallFaces[partId] = []
                  self.planarBoundaries[partId] = []
              v0 = feature.getCoordinate(0)
              v1 = feature.getCoordinate(1)
              if v0[0] != v1[0] or v0[1] != v1[1]:
                  z = float(feature.getAttribute('__ssc.elevation'))
                  v2 = (v1[0], v1[1], z)
                  v3 = (v0[0], v0[1], z)
                  boundary = fmeobjects.FMELine([v0, v1, v2, v3, v0])
                  self.wallFaces[partId].append(fmeobjects.FMEFace(boundary, fmeobjects.FME_CLOSE_3D_AVERAGE_MODE))
                  self.planarBoundaries[partId].append(v2)
                  self.feature = feature

          def close(self):
              self.outputSurface()

          def outputSurface(self):
              for partId in sorted(self.wallFaces.keys()):
                  wallFaces = self.wallFaces[partId]
                  planarBoundaries = self.planarBoundaries[partId]
                  if wallFaces:
                      sidewall = fmeobjects.FMECompositeSurface()
                      for face in wallFaces:
                          sidewall.appendPart(face)
                      self.feature.setGeometry(sidewall)
                      self.feature.setAttribute('__ssc.type', 'side')
                      self.pyoutput(self.feature)

                      planarBoundaries.append(planarBoundaries[0])
                      planar = fmeobjects.FMEPolygon(fmeobjects.FMELine(planarBoundaries))
                      self.feature.setGeometry(planar)
                      self.feature.setAttribute('__ssc.type', 'planar')
                      self.pyoutput(self.feature)
    PYTHONSYMBOL = BRepSolidBoundaryCreator
    -> Tester_3
Tester_3
    BOOL_OP = OR
    TEST_CLAUSE = TEST @Value(__ssc.type) = side
    TEST_MODE = Automatic
    PASSED -> Junction_5
    FAILED -> DonutBuilder [off]
Note: Sides
Junction_5
    -> Aggregator [off]
DonutBuilder
    ALLOW_CYCLES = No
    CONNECT_Z_MODE = First Wins
    DROP = yes
    GROUP_BY = __ssc.id
    AREA -> FaceReplacer
FaceReplacer
    ANGULAR_TOLERANCE_CHOICE = Automatic
    THICKNESS_TOLERANCE_CHOICE = Automatic
    -> Tester_4
Tester_4
    BOOL_OP = OR
    TEST_CLAUSE = TEST 0 < @Value(__ssc.flag)
    TEST_MODE = Automatic
    PASSED -> Top_2
    FAILED -> Bottom_2
Note: Tester 2: Passed
Top_2: Junction
    -> Aggregator
Note: Orientor: Oriented
Bottom_2: Junction
    -> Aggregator
Note: Output
Junction_7
    -> Junction_9
AttributeCreator_2
    ATTR_TABLE = SET_TO _rejected_reason = specified elevation is within zmin and zmax of seed surface
    -> Junction_3
AttributeCreator_3
    ATTR_TABLE = SET_TO _rejected_reason = unsupported geometry type
    -> Junction_3
Junction_3
    -> Inspector_2
Note: Rejected
Inspector_2

Bookmark: Terrain Solid Model
Aggregator
    ACCUM_ATTRS_NAME = Use Attributes From One Feature
    AGGREGATE_TYPE = Homogeneous Collection (If Possible)
    MODE = Geometry - Assemble One Level
    ORDERED = No
    SEP = ,
    AGGREGATE -> GeometryCoercer_3
GeometryCoercer_3
    GQUERY:
      for $geom in //geometry
      where $geom/count(parent::geometry) = 0
      return number($geom/@fme_id)
    KIND = fme_brep_solid
    COERCED -> Junction_7

Bookmark: 1102
3DForcer_2
    KEEPZVAL = No
    ZVALATTR = (@Value(z.min)-2.5)/2
    -> Extruder_5
Extruder_5
    DIRECTION = Vertical
    DISTANCE = 30-((@Value(z.min)-2.5)/2)
    EXTRUDED -> Junction_18

Bookmark: 1107
3DForcer_17
    KEEPZVAL = No
    ZVALATTR = (@Value(z.min)-2.5)/2
    -> Extruder_17
Extruder_17
    DIRECTION = Vertical
    DISTANCE = 30-((@Value(z.min)-2.5)/2)
    EXTRUDED -> Junction_18

Bookmark: 1108
3DForcer_16
    KEEPZVAL = No
    ZVALATTR = (@Value(z.min)-2.5)/2
    -> Extruder_16
Extruder_16
    DIRECTION = Vertical
    DISTANCE = 25-((@Value(z.min)-2.5)/2)
    EXTRUDED -> Junction_18

Bookmark: 1111
3DForcer_14
    KEEPZVAL = No
    ZVALATTR = (@Value(z.min)-1.5)/2
    -> Extruder_14
Extruder_14
    DIRECTION = Vertical
    DISTANCE = 25-((@Value(z.min)-2.5)/2)
    EXTRUDED -> Junction_18

Bookmark: 1114
3DForcer_11
    KEEPZVAL = No
    ZVALATTR = (@Value(z.min)-2.5)/2
    -> Extruder_11
Extruder_11
    DIRECTION = Vertical
    DISTANCE = 35-((@Value(z.min)-2.5)/2)
    EXTRUDED -> Junction_18

Bookmark: 1109
3DForcer_10
    KEEPZVAL = No
    ZVALATTR = (@Value(z.min)-1.5)/2
    -> Extruder_10
Extruder_10
    DIRECTION = Vertical
    DISTANCE = 30-((@Value(z.min)-1.5)/2)
    EXTRUDED -> Junction_18 [off]

Bookmark: 1110
3DForcer_15
    KEEPZVAL = No
    ZVALATTR = (@Value(z.min)-1.5)/2
    -> Extruder_15
Extruder_15
    DIRECTION = Vertical
    DISTANCE = 30-((@Value(z.min)-1.5)/2)
    EXTRUDED -> Junction_18 [off]

Bookmark: 1112
3DForcer_13
    KEEPZVAL = No
    ZVALATTR = (@Value(z.min)-1.5)/2
    -> Extruder_13
Extruder_13
    DIRECTION = Vertical
    DISTANCE = 30-((@Value(z.min)-1.5)/2)
    EXTRUDED -> Junction_18 [off]

Bookmark: 1113
3DForcer_12
    KEEPZVAL = No
    ZVALATTR = (@Value(z.min)-1.5)/2
    -> Extruder_12
Extruder_12
    DIRECTION = Vertical
    DISTANCE = 30-((@Value(z.min)-1.5)/2)
    EXTRUDED -> Junction_18 [off]
